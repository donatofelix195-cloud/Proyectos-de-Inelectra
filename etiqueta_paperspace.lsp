;;; --- DASHBOARD CABLE MANAGEMENT PRO v120.0.2 ---
;;; v120.0.2: Fix FIX_ALL_CONDUITS (VLA-Object error), Enhanced Stability.
;;; v120.0.1: Heuristic Shield (Blocks AutoCAD Handles), Tag Sanitizer v2,
;;; v120.0.1: Pattern Match *-*-*, Silent Audit Points, Layer Status NA.
;; --- 1. BASES DE DATOS DE CABLES ---
(setq *MARLEW_DATA* '(
    ("10COND#12AWG" 19.30) ("10COND#14AWG" 17.30) ("10COND#16AWG" 15.00) ("10CT+PIT#16AWG" 28.00)
    ("12COND#12AWG" 19.90) ("12COND#14AWG" 17.90) ("12COND#16AWG" 15.40) ("12PR#14AWG" 25.00)
    ("12PR#16AWG" 19.80) ("12PR+PIT#16AWG" 21.20) ("12PR+PIT#20AWG" 15.60) ("12PR+PT#18AWG" 17.70)
    ("12TR+P#20AWG" 18.70) ("12TR+PIT#16AWG" 25.10) ("12TR+PIT#18AWG" 21.60) ("14COND#12AWG" 21.30)
    ("14COND#14AWG" 19.10) ("14COND#16AWG" 16.40) ("16PR#16AWG" 22.00) ("16PR+PIT#16AWG" 24.00)
    ("16PR+PT#18AWG" 19.40) ("19COND#12AWG" 24.60) ("19COND#14AWG" 21.10) ("19COND#16AWG" 18.00)
    ("1PR#12AWG" 10.00) ("1PR#14AWG" 8.70) ("1PR#16AWG" 7.20) ("1PR#18AWG" 6.60)
    ("1PR#20AWG" 5.90) ("1PR+PIT#16AWG" 7.30) ("1PR+PIT#20AWG" 6.00) ("1PR+PT#18AWG" 6.70)
    ("1TR+P#20AWG" 6.30) ("1TR+PIT#16AWG" 7.70) ("1TR+PIT#18AWG" 7.00) ("24COND#12AWG" 28.10)
    ("24COND#14AWG" 25.10) ("24COND#16AWG" 20.50) ("24PR#14AWG" 34.40) ("24PR#16AWG" 27.40)
    ("24PR+PIT#16AWG" 29.40) ("24PR+PIT#20AWG" 21.40) ("24PR+PT#18AWG" 24.30) ("24TR+PIT#16AWG" 34.60)
    ("24TR+PIT#18AWG" 29.90) ("2COND#12AWG" 11.00) ("2COND#14AWG" 10.00) ("2COND#16AWG" 8.80)
    ("2CT+PIT#16AWG" 14.00) ("2PR#14AWG" 12.10) ("2PR#16AWG" 10.00) ("2PR+PIT#16AWG" 10.00)
    ("2PR+PT#18AWG" 9.30) ("2TR+PIT#16AWG" 13.40) ("2TR+PIT#18AWG" 12.00) ("36PR#16AWG" 31.20)
    ("36PR+PIT#16AWG" 34.00) ("36PR+PT#18AWG" 27.50) ("37COND#12AWG" 32.30) ("37COND#14AWG" 28.80)
    ("37COND#16AWG" 24.60) ("3COND#16AWG" 9.00) ("3PR+PIT#16AWG SI" 12.00) ("48COND#12AWG" 36.40)
    ("48COND#14AWG" 32.40) ("48COND#16AWG" 27.50) ("4COND#12AWG" 12.70) ("4COND#14AWG" 11.50)
    ("4COND#16AWG" 10.00) ("4CT+PIT#16AWG" 17.70) ("4PR#12AWG" 19.30) ("4PR#14AWG" 15.30)
    ("4PR#16AWG" 12.70) ("4PR+PIT#16AWG" 13.50) ("4PR+PIT#20AWG" 10.10) ("4PR+PT#18AWG" 11.50)
    ("4TR+P#20AWG" 12.00) ("4TR+PIT#16AWG" 15.40) ("4TR+PIT#18AWG" 13.70) ("6COND#16AWG" 10.50)
    ("6CT+PIT#16AWG" 21.20) ("6PR#14AWG" 18.70) ("6PR#16AWG" 14.90) ("6PR+PIT#16AWG" 15.90)
    ("6PR+PT#18AWG" 13.40) ("6TR+PIT#16AWG" 18.80) ("6TR+PIT#18AWG" 16.20) ("7COND#12AWG" 15.70)
    ("7COND#14AWG" 13.40) ("7COND#16AWG" 11.60) ("8COND#16AWG" 12.00) ("8PR#14AWG" 20.20)
    ("8PR#16AWG" 16.10) ("8PR+PIT#16AWG" 17.70) ("8PR+PIT#20AWG" 13.10) ("8PR+PT#18AWG" 14.40)
    ("8TR+P#20AWG" 15.20) ("8TR+PIT#16AWG" 20.30) ("8TR+PIT#18AWG" 18.00)
))
(setq *EKABEL_DATA* '(
    ("2COND#18AWG" 11.50) ("2COND#16AWG" 7.37) ("3COND#16AWG" 7.37) ("4COND#16AWG" 8.38)
    ("6COND#16AWG" 8.38) ("7COND#16AWG" 9.91) ("8COND#16AWG" 9.91) ("10COND#16AWG" 12.19)
    ("12COND#16AWG" 12.83) ("15COND#16AWG" 14.48) ("19COND#16AWG" 15.49) ("25COND#16AWG" 18.16)
    ("50COND#16AWG" 24.88) ("2COND#14AWG" 8.23) ("4COND#14AWG" 9.25) ("7COND#14AWG" 10.95)
    ("10COND#14AWG" 14.38) ("12COND#14AWG" 15.01) ("14COND#14AWG" 15.76) ("19COND#14AWG" 17.45)
    ("25COND#14AWG" 20.12) ("50COND#14AWG" 27.51) ("2COND#12AWG" 9.12) ("4COND#12AWG" 10.36)
    ("7COND#12AWG" 12.40) ("10COND#12AWG" 16.28) ("12COND#12AWG" 17.02) ("14COND#12AWG" 17.88)
    ("19COND#12AWG" 19.86) ("25COND#12AWG" 24.00) ("50COND#12AWG" 31.44) ("1PR#18AWG" 6.10)
    ("1PR#16AWG" 6.10) ("1PR+PT#18AWG" 6.35) ("2PR+PT#18AWG" 9.65) ("4PR+PT#18AWG" 11.93)
    ("6PR+PT#18AWG" 14.47) ("8PR+PT#18AWG" 14.22) ("12PR+PT#18AWG" 17.52) ("24PR+PT#18AWG" 24.88)
    ("36PR+PT#18AWG" 28.94) ("1PR#16AWG" 6.60) ("2PR#16AWG" 10.92) ("4PR#16AWG" 12.70)
    ("6PR#16AWG" 14.73) ("8PR#16AWG" 16.25) ("12PR#16AWG" 18.79) ("24PR#16AWG" 25.64)
    ("36PR#16AWG" 30.47) ("4PR#14AWG" 12.70) ("1PR+PIT#16AWG" 6.86) ("2PR+PIT#16AWG" 10.92)
    ("4PR+PIT#16AWG" 12.95) ("6PR+PIT#16AWG" 16.76) ("8PR+PIT#16AWG" 17.27) ("12PR+PIT#16AWG" 20.57)
    ("24PR+PIT#16AWG" 27.93) ("36PR+PIT#16AWG" 34.78) ("1TR+PIT#18AWG" 6.60) ("2TR+PIT#18AWG" 12.19)
    ("4TR+PIT#18AWG" 14.22) ("6TR+PIT#18AWG" 18.03) ("8TR+PIT#18AWG" 19.04) ("12TR+PIT#18AWG" 22.60)
    ("24TR+PIT#18AWG" 30.21) ("1TR+PIT#16AWG" 7.11) ("2TR+PIT#16AWG" 13.20) ("4TR+PIT#16AWG" 16.00)
    ("6TR+PIT#16AWG" 19.55) ("8TR+PIT#16AWG" 20.82) ("12TR+PIT#16AWG" 24.63) ("24TR+PIT#16AWG" 33.51)
    ("1PR#14AWG" 8.89) ("2PR#14AWG" 13.97) ("4PR#14AWG" 16.51) ("6PR#14AWG" 18.00)
    ("8PR#14AWG" 23.11) ("12PR#14AWG" 26.67) ("24PR#14AWG" 36.58) ("1PR#12AWG" 9.65)
    ("1PR#20AWG" 5.30) ("1TR+P#20AWG" 5.59) ("4TR+P#20AWG" 11.93) ("8TR+P#20AWG" 16.00)
    ("12TR+P#20AWG" 18.28) ("1PR+PIT#20AWG" 5.99) ("4PR+PIT#20AWG" 11.60) ("8PR+PIT#20AWG" 14.60)
    ("12PR+PIT#20AWG" 17.98) ("24PR+PIT#20AWG" 22.85)
))
(setq *ACTIVE_CATALOG_IDX* 0) (setq *CABLE_DATA* *MARLEW_DATA*)

;; --- 2. CORE ---
(defun CleanTag (s / res char i len) (if (and s (= (type s) 'STR)) (progn (setq s (strcase (vl-string-trim " " s)) res "" i 1 len (strlen s)) (while (<= i len) (setq char (substr s i 1)) (if (not (member char '(" " "_" "-"))) (setq res (strcat res char))) (setq i (1+ i))) res) ""))

(defun GetBlockRef (en / res parents obj)
  (if (and en (listp en) (> (length en) 2))
    (progn 
      (setq parents (reverse (last en)) res nil)
      (foreach p parents
        (if (not res)
          (progn 
            (setq obj (vlax-ename->vla-object p))
            (if (= (vla-get-ObjectName obj) "AcDbBlockReference") (setq res obj))
          )
        )
      )
      (if (not res) (setq res (vlax-ename->vla-object (last parents))))
    )
    (setq res (vlax-ename->vla-object (if (listp en) (car en) en)))
  ) res)

(defun GetAttrValue (en tag / vobj v found target current_tag) (setq target (CleanTag tag) v nil found nil vobj (if (= (type en) 'ENAME) (vlax-ename->vla-object en) en)) (if (and vobj (vlax-property-available-p vobj 'HasAttributes) (= (vla-get-HasAttributes vobj) :vlax-true)) (foreach at (vlax-invoke vobj 'GetAttributes) (setq current_tag (CleanTag (vla-get-TagString at))) (if (and (not found) (= current_tag target)) (setq v (vla-get-TextString at) found t)))) (if (not (and v (= (type v) 'STR))) (setq v "")) v)
(defun SetAttrValue (en tag val / vobj found target current_tag) (setq target (CleanTag tag) found nil val (vl-princ-to-string val)) (setq vobj (if (= (type en) 'ENAME) (vlax-ename->vla-object en) en)) (if (and vobj (vlax-property-available-p vobj 'HasAttributes) (= (vla-get-HasAttributes vobj) :vlax-true)) (foreach at (vlax-invoke vobj 'GetAttributes) (setq current_tag (CleanTag (vla-get-TagString at))) (if (= current_tag target) (progn (vla-put-TextString at val) (vla-update at) (setq found t))))) found)

(defun SetXDataHandle (en h / res) (regapp "MARLEW_LINK") (entmod (append (entget en) (list (list -3 (list "MARLEW_LINK" (cons 1000 h)))))))
(defun GetXDataHandle (en / xd) (if (and (setq xd (assoc -3 (entget en '("MARLEW_LINK")))) (cadr xd) (cadadr xd)) (cdr (cadadr xd)) ""))

(defun IncrementTag (str / i len num_str prefix num padding c)
  (setq len (strlen str) i len num_str "")
  (while (and (> i 0) (<= 48 (ascii (setq c (substr str i 1)))) (>= 57 (ascii c)))
    (setq num_str (strcat c num_str) i (1- i)))
  (if (> (strlen num_str) 0)
    (progn
      (setq prefix (substr str 1 i) num (1+ (atoi num_str)) padding "")
      (while (< (strlen padding) (- (strlen num_str) (strlen (itoa num)))) (setq padding (strcat padding "0")))
      (strcat prefix padding (itoa num))
    )
    (if (= str "") "01" (strcat str "-01"))
  )
)

;; --- 3. MAPEADO INTELIGENTE ---
(defun FindUltraSmartAttr (en base_tag / tags res i_num)
  (setq tags (list (strcat "T_" base_tag) base_tag))
  (cond 
    ((member (strcase base_tag) '("ELEV" "ELEVACION")) (setq tags (append tags '("T_ELEV" "ELEVACION" "ELEV" "T_ELEVACION"))))
    ((member (strcase base_tag) '("DIAMETRO" "DIAM")) (setq tags (append tags '("T_DIAMETRO" "DIAMETRO" "DIAM"))))
    ((member (strcase base_tag) '("PORCENTAJE" "PERCENT")) (setq tags (append tags '("T_PORCENTAJE" "PORCENTAJE"))))
    ((wcmatch (strcase base_tag) "CABLE_TIPO*") (setq i_num (substr base_tag (if (> (strlen base_tag) 10) 12 6)) tags (append tags (list (strcat "T_CABLE" i_num) (strcat "CABLE_" i_num) (strcat "CB" i_num)))))
    ((wcmatch (strcase base_tag) "CANTIDAD*") (setq i_num (substr base_tag (if (> (strlen base_tag) 8) 10 5)) tags (append tags (list (strcat "T_CANT" i_num) (strcat "CANT_" i_num) (strcat "QTY" i_num)))))
    ((member (strcase base_tag) '("TAG" "ID" "CONDUIT")) (setq tags (append tags '("T_CONDUIT" "TAG" "TRAMO" "T_TRAMO" "IDENT" "IDENTIFICADOR" "AREA" "ZONA" "ZT"))))
  )
  (setq res "") (foreach tg tags (if (and (= res "") (/= (GetAttrValue en tg) "")) (setq res (GetAttrValue en tg)))) res)

(defun SetUltraSmartAttr (en base_tag val / tags ok i_num)
  (setq tags (list (strcat "T_" base_tag) base_tag))
  (cond 
    ((member (strcase base_tag) '("ELEV" "ELEVACION")) (setq tags (append tags '("T_ELEV" "ELEVACION" "ELEV"))))
    ((member (strcase base_tag) '("DIAMETRO" "DIAM")) (setq tags (append tags '("T_DIAMETRO" "DIAMETRO"))))
    ((member (strcase base_tag) '("PORCENTAJE" "PERCENT")) (setq tags (append tags '("T_PORCENTAJE" "PORCENTAJE"))))
    ((wcmatch (strcase base_tag) "CABLE_TIPO*") (setq i_num (substr base_tag (if (> (strlen base_tag) 10) 12 6)) tags (append tags (list (strcat "T_CABLE" i_num) (strcat "CABLE_" i_num)))))
    ((wcmatch (strcase base_tag) "CANTIDAD*") (setq i_num (substr base_tag (if (> (strlen base_tag) 8) 10 5)) tags (append tags (list (strcat "T_CANT" i_num) (strcat "CANT_" i_num)))))
    ((member (strcase base_tag) '("TAG" "ID" "CONDUIT")) (setq tags (append tags '("T_CONDUIT" "TAG" "TRAMO" "T_TRAMO" "IDENT" "IDENTIFICADOR" "AREA" "ZONA" "ZT"))))
  )
  (setq ok nil) (foreach tg tags (if (not ok) (setq ok (SetAttrValue en tg val)))) ok)

;; --- 4. CALCULO ---
(defun GetSmartDiameter (cable_name / name res m)
  (setq name (CleanTag cable_name))
  (setq m (assoc name (mapcar '(lambda (x) (cons (CleanTag (car x)) (cadr x))) (if (= *ACTIVE_CATALOG_IDX* 0) *MARLEW_DATA* *EKABEL_DATA*))))
  (if m (setq res (cdr m))
    (progn (setq m (assoc name (mapcar '(lambda (x) (cons (CleanTag (car x)) (cadr x))) (if (= *ACTIVE_CATALOG_IDX* 0) *EKABEL_DATA* *MARLEW_DATA*))))
      (if m (setq res (cdr m)) (setq res 0.0))))
  res)

(defun GetInternalArea (diam_str / d target) 
  (setq target (CleanTag diam_str)) 
  (cond ((wcmatch target "*11/2*") (setq d 40.9)) ((wcmatch target "*3/4*") (setq d 20.9)) ((wcmatch target "*2*") (setq d 52.5)) ((wcmatch target "*1*") (setq d 26.6)) (t (setq d 20.9))) (* pi (/ (expt d 2) 4.0)))

(defun GetConduitData (obj / el diam i ca ta oc cl tl cv tv dc name pos lay_obj)
  (setq el (FindUltraSmartAttr obj "ELEVACION")) (if (= el "") (setq el "0.00"))
  (setq diam (FindUltraSmartAttr obj "DIAMETRO")) (if (= diam "") (setq diam "3/4\""))
  (setq name (FindUltraSmartAttr obj "TAG"))
  
  ;; --- FILTRO DE INGENIERIA ESTRÍCTO v120.0.1 (Inelectra Standard) ---
  ;; 1. Saneamiento Técnico (Limpia comentarios y basura visual)
  (if (setq pos (vl-string-search "(" name)) (setq name (vl-string-right-trim " " (substr name 1 pos))))
  (if (setq pos (vl-string-search " " name)) (setq name (substr name 1 pos)))
  
  ;; 2. Validación de Patrón y Visibilidad (Bloquea códigos internos ej. 57ADE4)
  (setq lay_obj (vla-item (vla-get-Layers (vla-get-ActiveDocument (vlax-get-acad-object))) (vla-get-Layer obj)))
  (if (or (= name "") (= name ".") (= (strcase name) "S/T")
          (wcmatch (strcase name) "*HIDDEN*") (wcmatch (strcase name) "*VISIBLE*")
          (not (wcmatch (strcase name) "*-*-*")) ; <--- Exige formato B600-TS-001
          (= (vla-get-LayerOn lay_obj) :vlax-false)
          (= (vla-get-Freeze lay_obj) :vlax-true))
      (progn
        (setq name "N/A")
        ;; --- REPARACIÓN PERMANENTE v120.0.1 ---
        ;; Si el conducto tiene basura, forzamos N/A en su atributo físico
        (SetUltraSmartAttr obj "TAG" "N/A")
      )
  )

  (foreach sym '("EL. +" "EL.+" "EL+" "+") (while (wcmatch el (strcat "*" sym "*")) (setq el (vl-string-subst "" sym el))))
  (setq el (vl-string-left-trim " " (vl-string-right-trim " " el)))
  (foreach sym '("%%C" "Ø") (while (wcmatch diam (strcat "*" sym "*")) (setq diam (vl-string-subst "" sym diam))))
  (setq diam (vl-string-left-trim " " (vl-string-right-trim " " diam)))
  (setq ta 0.0 i 1 cl nil tl nil)
  (repeat 5 
    (setq tv (FindUltraSmartAttr obj (strcat "CABLE_TIPO_" (itoa i))) cv (FindUltraSmartAttr obj (strcat "CANTIDAD_" (itoa i))))
    (if (and tv (/= (CleanTag tv) "")) 
      (progn (setq cl (cons (if (and cv (/= cv "")) cv "1") cl) tl (cons tv tl) dc (GetSmartDiameter tv)) 
             (if (> dc 0) (setq ta (+ ta (* (max 1.0 (atof (car cl))) (* pi (/ (expt dc 2) 4.0))))))))
    (setq i (1+ i)))

  ;; --- AUTO-SIZING DE INGENIERÍA (Cumplimiento <= 39%) ---
  (setq optimal_diam nil)
  (if (> ta 0.0)
    (progn
      (foreach d '("3/4\"" "1\"" "1 1/2\"" "2\"")
        (if (and (not optimal_diam) (<= (* (/ ta (GetInternalArea d)) 100.0) 39.0))
          (setq optimal_diam d)))
      (if (not optimal_diam) (setq optimal_diam "2\""))
    )
    (setq optimal_diam "3/4\"")
  )
  
  (setq diam optimal_diam ca (GetInternalArea diam))
  (setq oc (rtos (* (/ ta ca) 100.0) 2 2)) 
  (list el diam oc (reverse tl) (reverse cl) name (vla-get-Handle obj)))

(defun ApplyDataToTag (tag_obj data / el diam oc tl cl i name bn pos parent_h rem)
  (setq el (nth 0 data) diam (nth 1 data) oc (nth 2 data) tl (nth 3 data) cl (nth 4 data) name (nth 5 data) parent_h (nth 6 data))
  (setq bn (strcase (vla-get-EffectiveName tag_obj)))
  (SetUltraSmartAttr tag_obj "ELEVACION" (strcat "EL. +" el))
  (SetUltraSmartAttr tag_obj "PORCENTAJE" (strcat oc "%"))
  (if (or (wcmatch bn "*BAND*") (wcmatch bn "*TAG*"))
      (setq diam (strcat "%%C" (if (wcmatch diam "%%C*") (substr diam 4) diam))))
  (SetUltraSmartAttr tag_obj "DIAMETRO" diam)
  (if (wcmatch bn "*AREA_IDENT*")
    (progn 
      (setq pos (vl-string-search "-" name))
      (if pos 
        (progn 
          (SetUltraSmartAttr tag_obj "AREA" (substr name 1 pos))
          (setq rem (substr name (+ pos 2)))
          (while (vl-string-search "-" rem) (setq rem (vl-string-subst "" "-" rem)))
          (SetUltraSmartAttr tag_obj "IDENT" rem))
        (SetUltraSmartAttr tag_obj "IDENT" name)))
    (SetUltraSmartAttr tag_obj "TAG" name)
  )
  (setq i 1) (repeat 5 (SetUltraSmartAttr tag_obj (strcat "CABLE_TIPO_" (itoa i)) "") (SetUltraSmartAttr tag_obj (strcat "CANTIDAD_" (itoa i)) "") (setq i (1+ i)))
  (setq i 1) (foreach cb tl (SetUltraSmartAttr tag_obj (strcat "CABLE_TIPO_" (itoa i)) cb) (setq i (1+ i)))
  (setq i 1) (foreach qt cl (SetUltraSmartAttr tag_obj (strcat "CANTIDAD_" (itoa i)) qt) (setq i (1+ i)))
  (vl-catch-all-apply 'SetVisibilityState (list tag_obj (strcat "CB" (itoa (length tl)))))
  (if (and parent_h (/= parent_h "")) (progn (SetXDataHandle (vlax-vla-object->ename tag_obj) parent_h) (SetUltraSmartAttr tag_obj "HANDLE" parent_h)))
  (vla-update tag_obj))

(defun BroadcastConduitData (conduit_obj / data cur_hand ss_f j en_f obj_f bn_f cur_id)
  (setq data (GetConduitData conduit_obj)
        cur_hand (vla-get-Handle conduit_obj)
        cur_id (nth 5 data))
  (if (setq ss_f (ssget "X" '((0 . "INSERT"))))
    (progn 
      (setq j 0) 
      (repeat (sslength ss_f) 
        (setq en_f (ssname ss_f j) 
              obj_f (vlax-ename->vla-object en_f) 
              bn_f (if (vlax-property-available-p obj_f 'EffectiveName) (strcase (vla-get-EffectiveName obj_f)) ""))
        (if (or (wcmatch bn_f "*BAND*") (wcmatch bn_f "*AREA_IDENT*"))
          (if (or (= (GetXDataHandle en_f) cur_hand) 
                  (and (= (GetXDataHandle en_f) "") 
                       (= (CleanTag (if (wcmatch bn_f "*AREA_IDENT*") 
                                       (strcat (GetAttrValue en_f "AREA") (GetAttrValue en_f "IDENT")) 
                                       (FindUltraSmartAttr en_f "TAG"))) 
                          (CleanTag cur_id))))
            (ApplyDataToTag obj_f data)))
        (setq j (1+ j)))))
)

(defun SetVisibilityState (blk_obj state_name / props ok prop_name) (setq props (vlax-invoke blk_obj 'GetDynamicBlockProperties) ok nil) (foreach p props (setq prop_name (vla-get-PropertyName p)) (if (and (not ok) (wcmatch (strcase prop_name) "*VISIBILIDAD*,*VISIBILITY*")) (progn (vla-put-Value p (vlax-make-variant state_name 8)) (setq ok t)))) ok)

(setq *CLONE_MODE* nil)

(if (not *ULTIMO_TRAMO_ASIGNADO*) (setq *ULTIMO_TRAMO_ASIGNADO* "N/A"))

;; --- 5. DASHBOARD ---
(defun InternalCablePicker (en / dcl_file dcl_id f filtered cur_slot oc_val i diam_list cur_diam raw_el st loop obj_copy old_err cur_elev cats RefreshList update_oc data_copy data_tl data_cl cx1 cx2 cx3 cx4 cx5 qx1 qx2 qx3 qx4 qx5 cur_id f_c f_q f_oc f_d f_e f_id cur_hand final_data ss_f j en_f obj_f bn_f UpdateData ent_pull sub_loop cur_ent s_val info_label ss_test existe_real max_tag val_tag)
  
  ;; --- 0. PURGA DE MEMORIA (v120.0.1) ---
  ;; Si la memoria tiene basura de sesiones previas, la limpiamos a N/A
  (if (and *ULTIMO_TRAMO_ASIGNADO* (not (wcmatch (strcase *ULTIMO_TRAMO_ASIGNADO*) "*-*-*")))
      (setq *ULTIMO_TRAMO_ASIGNADO* "N/A"))
  (setq existe_real nil max_tag nil)
  (setq ss_test (ssget "_X" '((0 . "INSERT") (66 . 1))))
  
  (if ss_test
      (progn
        (setq j 0)
        (repeat (sslength ss_test)
          (setq en_f (ssname ss_test j))
          (setq val_tag (FindUltraSmartAttr en_f "TAG"))
          
          ;; --- FILTRO DE PROTECCIÓN HEURÍSTICA (v120.0.1) ---
          ;; Ignoramos basura como handles (5800B4) o textos sin guiones
          (if (not (wcmatch (strcase val_tag) "*-*-*")) (setq val_tag "N/A"))
          
          ;; Verificamos si nuestra memoria todavía existe en el dibujo
          (if (and *ULTIMO_TRAMO_ASIGNADO* (/= *ULTIMO_TRAMO_ASIGNADO* "N/A") (= (CleanTag val_tag) (CleanTag *ULTIMO_TRAMO_ASIGNADO*)))
              (setq existe_real t))
          
          ;; Buscamos el número más alto solo entre TAGs válidos
          (if (and (/= val_tag "N/A") (/= val_tag ""))
              (if (or (not max_tag) (> (atof (vl-string-right-trim " " (vl-string-left-trim "ABCDEFGHIJKLMNOPQRSTUVWXYZabcdefghijklmnopqrstuvwxyz-" val_tag))) 
                                       (atof (vl-string-right-trim " " (vl-string-left-trim "ABCDEFGHIJKLMNOPQRSTUVWXYZabcdefghijklmnopqrstuvwxyz-" max_tag)))))
                  (setq max_tag val_tag)))
          (setq j (1+ j))))
  )

  ;; Si el bloque de la memoria NO existe, saltamos al mas alto encontrado en el dibujo
  (if (not existe_real)
      (if max_tag 
          (setq *ULTIMO_TRAMO_ASIGNADO* max_tag)
          (setq *ULTIMO_TRAMO_ASIGNADO* "N/A"))
  )

  (setq info_label (if (and *ULTIMO_TRAMO_ASIGNADO* (/= *ULTIMO_TRAMO_ASIGNADO* "N/A")) *ULTIMO_TRAMO_ASIGNADO* "N/A"))

  (if *CLONE_MODE* (progn (princ "\n>>> Dashboard ya abierto. <<<") (setq *CLONE_MODE* nil) (princ))) 
  (setq *CLONE_MODE* t *DBLCLK_BACKUP* (getvar "DBLCLKEDIT")) (setvar "DBLCLKEDIT" 0)
  
  (setq old_err *error*
        *error* (lambda (msg)
                  (if (and dcl_id (> dcl_id 0)) (unload_dialog dcl_id))
                  (setvar "DBLCLKEDIT" *DBLCLK_BACKUP*)
                  (setq *CLONE_MODE* nil *error* old_err)
                  (if (and dcl_file (findfile dcl_file)) (vl-file-delete dcl_file))
                  (princ (strcat "\nError: " msg))))

  (setq diam_list '("3/4\"" "1\"" "1 1/2\"" "2\"") cats '("MARLEW" "Ekabel"))
  
  (defun RefreshList () (start_list "l_box") (foreach cl filtered (add_list (strcat (car cl) " | " (rtos (cadr cl) 2 2) "mm"))) (end_list))
  (defun UpdateData (idx) (setq *ACTIVE_CATALOG_IDX* idx *CABLE_DATA* (if (= idx 0) *MARLEW_DATA* *EKABEL_DATA*)) (setq filtered *CABLE_DATA*) (RefreshList))
  (defun update_oc (/ ta oc tv qv d_val ca_p it d_cable) 
    (setq d_val (nth (atoi (get_tile "d_pop")) diam_list) ca_p (GetInternalArea d_val) ta 0.0) 
    (setq it 1) (repeat 5 
      (setq tv (get_tile (strcat "c" (itoa it))) qv (get_tile (strcat "q" (itoa it))))
      (if (and tv (/= tv "")) (progn (setq d_cable (GetSmartDiameter tv)) (if (> d_cable 0) (setq ta (+ ta (* (max 1.0 (atof qv)) (* pi (/ (expt d_cable 2) 4.0))))))))
      (setq it (1+ it))) 
    (setq oc (* (/ ta ca_p) 100.0) oc_val oc) 
    (set_tile "oc_tx" (strcat "OCUPACION: " (rtos oc 2 2) "%")))

  (setq cur_diam (FindUltraSmartAttr en "DIAMETRO")) (if (= cur_diam "") (setq cur_diam "3/4\""))
  (setq raw_el (FindUltraSmartAttr en "ELEVACION") cur_elev raw_el) (if (wcmatch cur_elev "EL. +*") (setq cur_elev (substr cur_elev 6)))
  
  ;; --- 2. AUTOMATIZACION DE VALOR INICIAL (v120.0.1) ---
  (setq cur_id (vl-string-trim " " (FindUltraSmartAttr en "TAG")))
  
  ;; Si el bloque tiene basura (ID de autocad) o esta vacio, DEJAMOS N/A POR DEFECTO
  (if (or (= cur_id "") (= cur_id "???") (not (wcmatch (strcase cur_id) "*-*-*"))) 
      (setq cur_id "N/A"))

  (setq i 1) (repeat 5 (set (read (strcat "cx" (itoa i))) (FindUltraSmartAttr en (strcat "CABLE_TIPO_" (itoa i)))) (set (read (strcat "qx" (itoa i))) (FindUltraSmartAttr en (strcat "CANTIDAD_" (itoa i)))) (setq i (1+ i)))

  (setq dcl_file (vl-filename-mktemp "dashboard.dcl") f (open dcl_file "w"))
  (write-line "db_dlg : dialog { label=\"Dashboard Pro (v120.0.1 - Inelectra Standard)\";" f)
  (write-line "  :column {" f)
  (write-line "    :boxed_column { label=\"Gestion de TAG y Tramo\";" f)
  (write-line (strcat "      :text { key=\"last_info\"; label=\"ULTIMO DETECTADO EN PLANO: " info_label "\"; }") f)
  (write-line "      :row { :edit_box { key=\"id_box\"; label=\"ID Actual:\"; edit_width=20; } :button { key=\"btn_inc\"; label=\"+1\"; width=4; } :button { key=\"btn_na\"; label=\"N/A\"; width=4; } }" f)
  (write-line "    }" f)
  (write-line "    :row {" f)
  (write-line "      :boxed_column { label=\"Catalogo de Cables\";" f)
  (write-line "        :popup_list { key=\"cat_pop\"; label=\"Fabricante:\"; }" f)
  (write-line "        :edit_box { key=\"f_edit\"; label=\"Filtro:\"; }" f)
  (write-line "        :list_box { key=\"l_box\"; height=15; width=30; }" f)
  (write-line "      }" f)
  (write-line "      :boxed_column { label=\"Datos del Conducto\";" f)
  (write-line "        :boxed_row { label=\"Dimensiones\";" f)
  (write-line "          :popup_list { key=\"d_pop\"; label=\"D:\"; width=10; }" f)
  (write-line "          :edit_box { key=\"e_box\"; label=\"EL:\"; width=8; }" f)
  (write-line "        }" f)
  (foreach it '("1" "2" "3" "4" "5") 
    (write-line (strcat "        :row { :toggle { key=\"rb" it "\"; } :edit_box { key=\"c" it "\"; edit_width=20; } :edit_box { key=\"q" it "\"; edit_width=3; } }") f)
  )
  (write-line "        :boxed_column { label=\"Resultado de Ocupacion\";" f)
  (write-line "          :text { key=\"oc_tx\"; label=\"OCUPACION : 0.00%\"; }" f)
  (write-line "          :row { :button { key=\"btn_calc\"; label=\"CALCULAR\"; } :button { key=\"btn_copy\"; label=\"CLONAR\"; } }" f)
  (write-line "        }" f)
  (write-line "        :row {" f)
  (write-line "          :button { key=\"accept\"; label=\"GUARDAR DATOS\"; is_default=true; }" f)
  (write-line "          :button { key=\"cancel\"; label=\"Cerrar\"; is_cancel=true; }" f)
  (write-line "        }" f)
  (write-line "      }" f)
  (write-line "    }" f)
  (write-line "  }" f)
  (write-line "}" f) (close f)

  (setq loop t cur_slot "1")
  (while loop
    (setq dcl_id (load_dialog dcl_file))
    (if (and dcl_id (> dcl_id 0) (new_dialog "db_dlg" dcl_id))
      (progn 
        (start_list "cat_pop") (foreach c cats (add_list c)) (end_list) (set_tile "cat_pop" (itoa *ACTIVE_CATALOG_IDX*))
        (start_list "d_pop") (foreach d diam_list (add_list d)) (end_list) (set_tile "d_pop" (itoa (cond ((vl-position cur_diam diam_list)) (0))))
        (set_tile "e_box" cur_elev) (set_tile "id_box" cur_id)
        (foreach it '("1" "2" "3" "4" "5") (set_tile (strcat "c" it) (vl-princ-to-string (eval (read (strcat "cx" it))))) (set_tile (strcat "q" it) (vl-princ-to-string (eval (read (strcat "qx" it))))))
        (set_tile (strcat "rb" cur_slot) "1") (UpdateData *ACTIVE_CATALOG_IDX*) (update_oc)
        (action_tile "cat_pop" "(UpdateData (atoi $value)) (update_oc)")
        (action_tile "d_pop" "(update_oc)")
        (action_tile "btn_inc" (strcat "(progn (setq val_inc (get_tile \"id_box\")) "
                                       "(if (or (= (strcase val_inc) \"N/A\") (= val_inc \"\") (= val_inc \"???\")) "
                                       "    (setq val_base (if (and *ULTIMO_TRAMO_ASIGNADO* (/= *ULTIMO_TRAMO_ASIGNADO* \"N/A\")) *ULTIMO_TRAMO_ASIGNADO* \"A000-XX-000\")) "
                                       "    (setq val_base val_inc)) "
                                       "(set_tile \"id_box\" (IncrementTag val_base)))"))
        (action_tile "btn_na" "(set_tile \"id_box\" \"N/A\")")
        (action_tile "f_edit" "(progn (setq filtered *CABLE_DATA* s_val (strcase (get_tile \"f_edit\")) filtered (vl-remove-if-not '(lambda (x) (wcmatch (strcase (car x)) (strcat \"*\" s_val \"*\"))) filtered)) (RefreshList))")
        (action_tile "l_box" "(progn (set_tile (strcat \"c\" cur_slot) (car (nth (atoi $value) filtered))) (update_oc))")
        (foreach it '("1" "2" "3" "4" "5") (action_tile (strcat "rb" it) (strcat "(setq cur_slot \"" it "\")")) (action_tile (strcat "c" it) "(update_oc)") (action_tile (strcat "q" it) "(update_oc)"))
        (action_tile "btn_calc" "(update_oc)")
        
        (action_tile "btn_copy" "(if (> oc_val 39.0) (alert \"ERROR DE INGENIERIA: La ocupacion excede el limite de 39%.\") (progn (setq f_c (list (get_tile \"c1\") (get_tile \"c2\") (get_tile \"c3\") (get_tile \"c4\") (get_tile \"c5\")) f_q (list (get_tile \"q1\") (get_tile \"q2\") (get_tile \"q3\") (get_tile \"q4\") (get_tile \"q5\")) f_oc (rtos oc_val 2 2) f_d (nth (atoi (get_tile \"d_pop\")) diam_list) f_e (get_tile \"e_box\") f_id (vl-string-trim \" \" (get_tile \"id_box\"))) (if (or (= f_id \"\") (= f_id \" \")) (setq f_id \"N/A\")) (if (and (/= f_id \"\") (/= (strcase f_id) \"N/A\")) (setq *ULTIMO_TRAMO_ASIGNADO* f_id)) (done_dialog 2)))")
        (action_tile "accept" "(if (> oc_val 39.0) (alert \"ERROR DE INGENIERIA: La ocupacion excede el limite de 39%.\") (progn (setq f_c (list (get_tile \"c1\") (get_tile \"c2\") (get_tile \"c3\") (get_tile \"c4\") (get_tile \"c5\")) f_q (list (get_tile \"q1\") (get_tile \"q2\") (get_tile \"q3\") (get_tile \"q4\") (get_tile \"q5\")) f_oc (rtos oc_val 2 2) f_d (nth (atoi (get_tile \"d_pop\")) diam_list) f_e (get_tile \"e_box\") f_id (vl-string-trim \" \" (get_tile \"id_box\"))) (if (or (= f_id \"\") (= f_id \" \")) (setq f_id \"N/A\")) (if (and (/= f_id \"\") (/= (strcase f_id) \"N/A\")) (setq *ULTIMO_TRAMO_ASIGNADO* f_id)) (done_dialog 1)))")
        (setq st (start_dialog)) (unload_dialog dcl_id)
        (if (= st 2) 
          (progn 
            (setq sub_loop t)
            (while sub_loop
              (if (and (setq ent_pull (nentselp "\nSELECCIONE BLOQUE MODELO: ")) (not (vl-catch-all-error-p ent_pull)))
                (progn 
                  (setq obj_copy (GetBlockRef ent_pull) data_copy (GetConduitData obj_copy))
                  (if (and data_copy (cadr data_copy))
                    (progn 
                      (setq cur_elev (car data_copy) cur_diam (cadr data_copy) data_tl (nth 3 data_copy) data_cl (nth 4 data_copy) cur_id (last data_copy))
                      (setq i 1) (repeat 5 (set (read (strcat "cx" (itoa i))) "") (set (read (strcat "qx" (itoa i))) "") (setq i (1+ i)))
                      (setq i 1) (foreach v data_tl (set (read (strcat "cx" (itoa i))) v) (setq i (1+ i)))
                      (setq i 1) (foreach v data_cl (set (read (strcat "qx" (itoa i))) v) (setq i (1+ i)))
                      (setq sub_loop nil)
                    )
                    (princ "\nNo reconocido. Reintente.")
                  )
                )
                (setq sub_loop nil)
              )
            )
            (setq loop t)
          )
          (setq loop nil)
        )
      )
      (progn (alert "Error DCL.") (setq loop nil))
    )
  )
  (if (= st 1) 
    (progn 
      (setq cur_hand (vla-get-Handle (if (= (type en) 'ENAME) (vlax-ename->vla-object en) en)))
      (setq i 1) (foreach v f_c (SetUltraSmartAttr en (strcat "CABLE_TIPO_" (itoa i)) v) (setq i (1+ i))) 
      (setq i 1) (foreach v f_q (SetUltraSmartAttr en (strcat "CANTIDAD_" (itoa i)) v) (setq i (1+ i))) 
      (SetUltraSmartAttr en "PORCENTAJE" (strcat f_oc "%")) (SetUltraSmartAttr en "DIAMETRO" f_d) 
      (SetUltraSmartAttr en "ELEVACION" (strcat "EL. +" f_e)) (SetUltraSmartAttr en "TAG" f_id)
      
      ;; --- SILENT VISUAL AUDIT ---
      (setq aud_lay (if (or (= (strcase f_id) "N/A") (= f_id "")) "_AUDIT_NA" "_AUDIT_TAGS"))
      (if (not (tblsearch "LAYER" aud_lay)) (entmake (list '(0 . "LAYER") '(100 . "AcDbSymbolTableRecord") '(100 . "AcDbLayerTableRecord") (cons 2 aud_lay) '(70 . 0) (cons 62 (if (= aud_lay "_AUDIT_NA") 1 3)))))
      (setq ip (vlax-get (if (= (type en) 'ENAME) (vlax-ename->vla-object en) en) 'InsertionPoint))
      (entmake (list '(0 . "POINT") (cons 10 ip) (cons 8 aud_lay)))
      (princ (strcat "\n[LISTO]: Paper v120 generado como [" f_id "] y marcado en auditoria."))

      (princ (strcat "\n[LISTO]: Paper v120 generado como [" f_id "] y marcado en auditoria."))
      (BroadcastConduitData (vlax-ename->vla-object (if (= (type en) 'ENAME) en (vlax-vla-object->ename en))))
      T) nil)
  (setvar "DBLCLKEDIT" *DBLCLK_BACKUP*) (setq *CLONE_MODE* nil) (setq *error* old_err) (princ))

(defun IsConduitBlock (obj / d t_val)
  (and 
    obj
    (= (type obj) 'VLA-OBJECT)
    (= (vla-get-ObjectName obj) "AcDbBlockReference")
    (vlax-property-available-p obj 'HasAttributes)
    (= (vla-get-HasAttributes obj) :vlax-true)
    ;; Filtro Estricto: Debe tener Diámetro y un TAG con formato o N/A
    (/= (FindUltraSmartAttr obj "DIAMETRO") "")
    (setq t_val (FindUltraSmartAttr obj "TAG"))
    (or (wcmatch (strcase t_val) "*-*-*") (= (strcase t_val) "N/A") (= t_val ""))
  )
)

(defun DoubleClickCallback (reactor info / pt ent obj found ss i)
  (setq found nil)
  (vl-catch-all-apply
    '(lambda ()
      ;; 1. Revisar PickFirst (si ya estaba seleccionado)
      (if (setq ss (cadr (ssgetfirst)))
        (progn
          (setq i 0)
          (while (and (not found) (< i (sslength ss)))
            (setq obj (vlax-ename->vla-object (ssname ss i)))
            (if (IsConduitBlock obj)
              (progn (InternalCablePicker obj) (setq found t)))
            (setq i (1+ i)))))
      
      ;; 2. Revisar punto del clic (nentselp)
      (if (not found)
        (progn 
          (setq pt (car info))
          (if (and (setq ent (nentselp pt))
                   (setq obj (GetBlockRef ent))
                   (IsConduitBlock obj))
            (progn (InternalCablePicker obj) (setq found t)))))))
  (princ))

;; --- 6. COMANDOS ---
(defun c:ETIQUETAR (/ ent obj data ins opt p1 p2 p2_obj p1_obj s u_f) 
  (vl-load-com) 
  (setq s (if (= (getvar "TILEMODE") 1) (/ 1.0 (getvar "CANNOSCALEVALUE")) 1.0))
  (setq u_f (if (= (getvar "MEASUREMENT") 0) (/ 1.0 25.4) 1.0))
  (initget "Bandera Area AMbos")
  (setq opt (cond ((getkword "\nTipo de etiqueta [Bandera/Area/AMbos] <Bandera>: ")) ("Bandera")))
  (if (setq ent (nentselp "\nSELECCIONE CONDUCTO ORIGEN: ")) 
    (progn 
      (setq obj (GetBlockRef ent) data (GetConduitData obj)) 
      (if (setq ins (getpoint "\nCLIC PARA INSERTAR ETIQUETA: ")) 
        (cond 
          ((= opt "Bandera")
           (if (tblsearch "BLOCK" "band")
             (ApplyDataToTag (vla-InsertBlock (if (= (getvar "TILEMODE") 1) (vla-get-ModelSpace (vla-get-ActiveDocument (vlax-get-acad-object))) (vla-get-PaperSpace (vla-get-ActiveDocument (vlax-get-acad-object)))) (vlax-3d-point ins) "band" s s s 0) data)
             (alert "Falta el bloque: band")))
          ((= opt "Area")
           (if (tblsearch "BLOCK" "AREA_IDENT")
             (ApplyDataToTag (vla-InsertBlock (if (= (getvar "TILEMODE") 1) (vla-get-ModelSpace (vla-get-ActiveDocument (vlax-get-acad-object))) (vla-get-PaperSpace (vla-get-ActiveDocument (vlax-get-acad-object)))) (vlax-3d-point ins) "AREA_IDENT" s s s 0) data)
             (alert "Falta el bloque: AREA_IDENT")))
          ((= opt "AMbos")
           (if (and (tblsearch "BLOCK" "band") (tblsearch "BLOCK" "AREA_IDENT"))
             (progn 
               (setq p2_obj (vl-catch-all-apply 'vla-InsertBlock (list (if (= (getvar "TILEMODE") 1) (vla-get-ModelSpace (vla-get-ActiveDocument (vlax-get-acad-object))) (vla-get-PaperSpace (vla-get-ActiveDocument (vlax-get-acad-object)))) (vlax-3d-point ins) "AREA_IDENT" s s s 0)))
               (if (not (vl-catch-all-error-p p2_obj)) (ApplyDataToTag p2_obj data))
               
               (setq p1 (list (+ (car ins) (* 9.0 s u_f)) (- (cadr ins) (* 3.5 s u_f)) (caddr ins)))
               (setq p1_obj (vl-catch-all-apply 'vla-InsertBlock (list (if (= (getvar "TILEMODE") 1) (vla-get-ModelSpace (vla-get-ActiveDocument (vlax-get-acad-object))) (vla-get-PaperSpace (vla-get-ActiveDocument (vlax-get-acad-object)))) (vlax-3d-point p1) "band" s s s 0)))
               (if (not (vl-catch-all-error-p p1_obj)) (ApplyDataToTag p1_obj data))
               
               (princ "\n>>> AMBOS INSERTADOS Y VINCULADOS <<<"))
             (alert "Error: Los bloques 'band' y 'AREA_IDENT' deben existir al mismo tiempo.")))
        )
      )
    )
  ) (princ))

(defun c:DASHBOARD () (vl-load-com) (if (setq e (nentselp "\nSeleccione conducto: ")) (progn (setq obj (GetBlockRef e)) (if (/= (FindUltraSmartAttr obj "DIAMETRO") "") (InternalCablePicker obj) (alert "No es conducto."))) (princ "\nCancelado.")) (princ))
(defun c:SYNC_TAG () (vl-load-com) (if (setq ent (nentselp "\nSELECCIONE ETIQUETA: ")) (progn (setq obj (GetBlockRef ent)) (if (setq src (nentselp "\nSELECCIONE CONDUCTO: ")) (ApplyDataToTag obj (GetConduitData (GetBlockRef src))) (princ "\nCancelado."))) (princ)) (princ))
(defun c:CLEAN_PLAN (/ ss i en obj name)
  (vl-load-com)
  (princ "\n>>> INICIANDO LIMPIEZA DE TRAMOS (Anti-Handles)... <<<")
  (if (setq ss (ssget "X" '((0 . "INSERT"))))
    (progn (setq i 0 j 0) (repeat (sslength ss) (setq en (ssname ss i) obj (vlax-ename->vla-object en))
        (if (and (vlax-property-available-p obj 'HasAttributes) (= (vla-get-HasAttributes obj) :vlax-true))
            (progn (setq name (FindUltraSmartAttr en "TAG"))
              (if (and (/= name "") (/= (strcase name) "N/A") (not (wcmatch (strcase name) "*-*")))
                  (progn (SetUltraSmartAttr en "TAG" "N/A") (vla-update obj) (setq j (1+ j)))))) (setq i (1+ i)))
      (princ (strcat "\n>>> LIMPIEZA COMPLETADA. ELEMENTOS SANADOS: " (itoa j) " <<<")))
    (princ "\nNo se encontraron bloques.")) (princ))

(defun c:FIX_ALL_CONDUITS () 
  (vl-load-com) 
  (princ "\n>>> INICIANDO ACTUALIZACION GLOBAL Y SINCRONIZACION... <<<")
  (if (setq ss (ssget "X" '((0 . "INSERT")))) 
    (progn 
      (setq i 0 j 0) 
      (repeat (sslength ss) 
        (setq en (ssname ss i) obj (vlax-ename->vla-object en)) 
        (if (and (IsConduitBlock obj) (vlax-property-available-p obj 'HasAttributes))
          (progn 
            ;; 1. Recalcular y Aplicar al propio conducto
            (ApplyDataToTag obj (GetConduitData obj)) 
            ;; 2. Sincronizar con todas sus etiquetas vinculadas
            (BroadcastConduitData obj)
            (setq j (1+ j))))
        (setq i (1+ i))) 
      (princ (strcat "\n>>> ACTUALIZADOS (" (itoa j) "/" (itoa i) ") <<<"))) 
    (princ "\nSin bloques.")) (princ))

(defun InitReactors () 
  (vl-load-com) 
  (foreach r (vlr-reactors :vlr-mouse-reactor) (foreach c (cdr r) (vlr-remove c)))
  (vlr-mouse-reactor "C" '((:vlr-beginDoubleClick . DoubleClickCallback)))
  (princ "\n>>> DASHBOARD MNGMT PRO v120.0.2 CARGADO. <<<")
  (princ "\n>>> Use 'CLEAN_PLAN' para purgar IDs internos de AutoCAD. <<<"))

(InitReactors) (princ)
