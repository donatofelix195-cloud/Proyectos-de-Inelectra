;;; --- EXCEL PRO v9.8.2 (METRICO) ---
;;; v9.8.2: Migración completa de lógica IN a MM. LB al 40%. Búsqueda dinámica Book3.csv.

(vl-load-com)

;; --- FUNCIONES AUXILIARES ---
(defun EX_GEX (n / a r) (setq a "") (while (> n 0) (setq r (rem (1- n) 26) a (strcat (chr (+ 65 r)) a) n (/ (1- n) 26))) a)
(defun EX_Clean (s) (if s (vl-string-trim " \t\r\n" s) ""))
(defun EX_Atof (s) (if s (atof (vl-string-translate "," "." (EX_Clean s))) 0.0))
(defun EX_FormatearFraccion (s) (cond ((= s "0.5") "1/2\"") ((= s "0.75") "3/4\"") ((= s "1") "1\"") ((= s "1.25") "1 1/4\"") ((= s "1.5") "1 1/2\"") ((= s "2") "2\"") ((= s "2.5") "2 1/2\"") ((= s "3") "3\"") ((= s "4") "4\"") (t (strcat s "\""))))

(defun EX_GBO (bn / d b r)
  (setq d (vla-get-Blocks (vla-get-ActiveDocument (vlax-get-acad-object))) r '())
  (if (not (vl-catch-all-error-p (setq b (vl-catch-all-apply 'vla-item (list d bn))))) 
    (vlax-for e b (if (= (vla-get-ObjectName e) "AcDbAttributeDefinition") (setq r (cons (vla-get-TagString e) r)))))
  (reverse r)
)

(defun EX_GCA (bn / d b r)
  (setq d (vla-get-Blocks (vla-get-ActiveDocument (vlax-get-acad-object))) r '())
  (if (not (vl-catch-all-error-p (setq b (vl-catch-all-apply 'vla-item (list d bn))))) 
    (vlax-for e b (if (and (= (vla-get-ObjectName e) "AcDbAttributeDefinition") (= (vla-get-Constant e) :vlax-true)) 
      (setq r (cons (cons (vla-get-TagString e) (vla-get-TextString e)) r)))))
  r
)

(defun EX_PIB (tg vl / n q r m pos)
  (setq q (chr 34) r nil n (distof vl))
  ;; --- MOTOR DE FILTRADO v9.8.2 ---
  (if (or (member (strcase tg) '("TAG" "TRAMO" "ID" "IDENT" "IDENTIFICADOR" "ID_TRAMO" "ID_TAG" "T_CONDUIT" "HANDLE"))
          (wcmatch (strcase tg) "*TRAMO*") (wcmatch (strcase tg) "*TAG*") (wcmatch (strcase tg) "*ID*"))
    (progn
      (if (setq pos (vl-string-search "(" vl)) (setq vl (vl-string-right-trim " " (substr vl 1 pos))))
      (if (setq pos (vl-string-search " " vl)) (setq vl (substr vl 1 pos)))
      (setq r (list "TXT" vl))
    )
  )
  
  (if (and (not r) n (/= vl ""))
    (cond 
      ((member (strcase tg) '("LONGITUD" "L" "LEN" "LENGTH" "LONG"))
       (setq m n) (if (< m 1000) (setq m 1000.0) (setq m (* (fix (+ (/ m 1000.0) 0.5)) 1000.0)))
       (setq r (list "WMM" (strcat (rtos (/ m 1000.0) 2 2) " m") m)))
      ((or (wcmatch (strcase tg) "*DIAM*") (wcmatch (strcase tg) "*REDUC*") (member (strcase tg) '("D" "DIA" "DIAMETRO")))
       (setq r (list "TXT" 
         (cond 
           ((equal n 0.75 0.01) "3/4\"")
           ((equal n 1.0 0.01)  "1\"")
           ((equal n 1.5 0.01)  "1 1/2\"")
           ((equal n 2.0 0.01)  "2\"")
           (t (strcat (rtos n 2 2) q))
         ))))
      ((member (strcase tg) '("PZ" "PZS" "CANT" "QTY" "CANTIDAD")) (setq r (list "NUM" (fix (+ n 0.999999)))))
      (t (setq r (list "NUM" n)))
    )
    (if (or (wcmatch (strcase tg) "*DIAM*") (wcmatch vl (strcat "*" q "*"))) (setq r (list "TXT" (strcat "'" vl))) (setq r (list "RAW" vl)))
  ) r
)

;; --- TRADUCTOR DE DIAMETROS ---
(defun EX_DiametroDecimal (dia)
  (cond
    ((= dia "1/2\"") "0.5")
    ((= dia "3/4\"") "0.75")
    ((= dia "1\"") "1")
    ((= dia "1 1/4\"") "1.25")
    ((= dia "1 1/2\"") "1.5")
    ((= dia "2\"") "2")
    ((= dia "2 1/2\"") "2.5")
    ((= dia "3\"") "3")
    ((= dia "4\"") "4")
    (t dia)
  )
)

;; --- LECTOR CSV ROBUSTO ---
(defun EX_ParseCSVLine (str / len i c inQuotes fld result nextC)
  (setq len (strlen str) i 1 inQuotes nil fld "" result '())
  (while (<= i len)
    (setq c (substr str i 1))
    (if (= c "\"")
      (progn
        (if (< i len) (setq nextC (substr str (1+ i) 1)) (setq nextC ""))
        (if (= nextC "\"")
          (progn (setq fld (strcat fld "\"") i (1+ i)))
          (setq inQuotes (not inQuotes))
        )
      )
      (if (and (= c ",") (not inQuotes))
        (progn (setq result (append result (list fld)) fld ""))
        (setq fld (strcat fld c))
      )
    )
    (setq i (1+ i))
  )
  (setq result (append result (list fld)))
  result
)

(defun EX_QuotesBalanced (str / i len inQuotes c)
  (setq i 1 len (strlen str) inQuotes nil)
  (while (<= i len)
    (setq c (substr str i 1))
    (if (= c "\"") (setq inQuotes (not inQuotes)))
    (setq i (1+ i))
  )
  (not inQuotes)
)

(defun EX_ReadFullCSVLine (fp / line next_line)
  (setq line (read-line fp))
  (if line
    (while (and (not (EX_QuotesBalanced line)) (setq next_line (read-line fp)))
      (setq line (strcat line " " next_line))
    )
  )
  line
)

;; --- OBTENER RUTA DINAMICA DE Book3.csv ---
(defun EX_GetCSVPath (/ p)
  (if (and *EX_CSV_PATH* (findfile *EX_CSV_PATH*))
    *EX_CSV_PATH*
    (progn
      (setq p (cond
        ((findfile (strcat (getvar "DWGPREFIX") "Book3.csv")))
        ((findfile "Book3.csv"))
        ((and (setq p (findfile "excel_extraer_mm.lsp"))
              (setq p (strcat (vl-filename-directory p) "\\Book3.csv"))
              (findfile p)) p)
        (t nil)
      ))
      (if (not p) (setq p (getfiled "No se encontro Book3.csv automáticamente. Por favor, selecciónelo:" "Book3.csv" "csv" 16)))
      (setq *EX_CSV_PATH* p)
    )
  )
)

;; --- FUNCIONES DE BUSQUEDA EN CSV ---
(defun EX_BuscarDentCode (diametro forma material unidad tipo / csv_path fp line fields col_a col_b fq ft pat_mat pat_forma pat_tipo result fallback_result fallback_desc found d_num)
  (setq csv_path (EX_GetCSVPath))
  (setq d_num (EX_Atof diametro) result nil fallback_result nil fallback_desc nil found nil)
  (setq fp (open csv_path "r"))
  (if fp
    (progn
      (setq pat_mat (strcase (if (wcmatch (strcase material) "*GALV*") "*GALV*" (strcat "*" material "*"))))
      (setq pat_forma (strcase (strcat "*FORMA*" forma "*")))
      (setq pat_tipo (if (and tipo (/= tipo "")) (strcase (strcat "*TIPO " (chr 34) tipo (chr 34) "*")) nil))
      (read-line fp)
      (while (and (not found) (setq line (EX_ReadFullCSVLine fp)))
        (setq fields (EX_ParseCSVLine line))
        (if (>= (length fields) 17)
          (progn
            (setq col_a (EX_Clean (nth 0 fields)) col_b (strcase (nth 1 fields)) fq (nth 16 fields))
            (if (and (or (not unidad) (<= (length fields) 19) (wcmatch (strcase (nth 19 fields)) "*IN*"))
                     (or (= (EX_Atof fq) d_num) (< (abs (- (EX_Atof fq) d_num)) 0.05))
                     (wcmatch col_b "*CONDULETA*")
                     (wcmatch col_b pat_mat)
                     (or (not pat_tipo) (wcmatch col_b pat_tipo)))
              (if (wcmatch col_b pat_forma)
                (progn (setq result col_a *ultima_desc* col_b found T))
                (if (not fallback_result) (setq fallback_result col_a fallback_desc col_b))
              )
            )
          )
        )
      )
      (close fp)
      (if (not result) (progn (setq result fallback_result) (if fallback_desc (setq *ultima_desc* fallback_desc))))
    )
  )
  result
)

(defun EX_BuscarTapaCode (diametro forma material / csv_path fp line fields col_a col_b fq result fallback_result found d_num pat_mat pat_forma)
  (setq csv_path (EX_GetCSVPath))
  (setq d_num (EX_Atof diametro) result nil fallback_result nil found nil)
  (setq fp (open csv_path "r"))
  (if fp
    (progn
      (setq pat_mat (strcase (if (wcmatch (strcase material) "*GALV*") "*GALV*" (strcat "*" material "*"))))
      (setq pat_forma (strcase (strcat "*FORMA*" forma "*")))
      (read-line fp)
      (while (and (not found) (setq line (EX_ReadFullCSVLine fp)))
        (setq fields (EX_ParseCSVLine line))
        (if (>= (length fields) 17)
          (progn
            (setq col_a (EX_Clean (nth 0 fields)) col_b (strcase (nth 1 fields)) fq (nth 16 fields))
            (if (and (or (<= (length fields) 19) (wcmatch (strcase (nth 19 fields)) "*IN*"))
                     (or (= (EX_Atof fq) d_num) (< (abs (- (EX_Atof fq) d_num)) 0.05))
                     (wcmatch col_b "*TAPA*CONDULETA*")
                     (wcmatch col_b pat_mat))
              (if (wcmatch col_b pat_forma)
                (progn (setq result col_a found T))
                (if (not fallback_result) (setq fallback_result col_a))
              )
            )
          )
        )
      )
      (close fp)
      (if (not result) (setq result fallback_result))
    )
  )
  result
)

(defun EX_BuscarEmpaCode (diametro forma material / csv_path fp line fields col_a col_b fq result fallback_result found desc_pattern d_num pat_forma)
  (setq csv_path (EX_GetCSVPath))
  (setq d_num (EX_Atof diametro))
  (setq desc_pattern (if (or (< (abs (- d_num 0.5)) 0.05) (< (abs (- d_num 0.75)) 0.05) (< (abs (- d_num 1.0)) 0.05)) "*EMPACADURA*SOLIDA*" "*EMPACADURA*ABIERTA*"))
  (setq result nil fallback_result nil found nil)
  (setq fp (open csv_path "r"))
  (if fp
    (progn
      (setq pat_forma (strcase (strcat "*FORMA*" forma "*")))
      (read-line fp)
      (while (and (not found) (setq line (EX_ReadFullCSVLine fp)))
        (setq fields (EX_ParseCSVLine line))
        (if (>= (length fields) 17)
          (progn
            (setq col_a (EX_Clean (nth 0 fields)) col_b (strcase (nth 1 fields)) fq (nth 16 fields))
            (if (and (or (<= (length fields) 19) (wcmatch (strcase (nth 19 fields)) "*IN*"))
                     (or (= (EX_Atof fq) d_num) (< (abs (- (EX_Atof fq) d_num)) 0.05))
                     (wcmatch col_b "*EMPACADURA*")
                     (wcmatch col_b desc_pattern))
              (if (wcmatch col_b pat_forma)
                (progn (setq result col_a found T))
                (if (not fallback_result) (setq fallback_result col_a))
              )
            )
          )
        )
      )
      (close fp)
      (if (not result) (setq result fallback_result))
    )
  )
  result
)

(defun EX_BuscarUnionCode (diametro material / csv_path fp line fields col_a col_b fq result found d_num pat_mat)
  (setq csv_path (EX_GetCSVPath))
  (setq d_num (atof diametro) result nil found nil)
  (setq fp (open csv_path "r"))
  (if fp
    (progn
      (setq pat_mat (if (wcmatch (strcase material) "*GALV*") "*GALV*" (strcat "*" (strcase material) "*")))
      (read-line fp)
      (while (and (not found) (setq line (EX_ReadFullCSVLine fp)))
        (setq fields (EX_ParseCSVLine line))
        (if (>= (length fields) 17)
          (progn
            (setq col_a (nth 0 fields) col_b (nth 1 fields) fq (nth 16 fields))
            (if (and (or (<= (length fields) 19) (wcmatch (strcase (nth 19 fields)) "*IN*"))
                     (or (= (atof fq) d_num) (< (abs (- (atof fq) d_num)) 0.02))
                     (wcmatch (strcase col_b) "*UNION*")
                     (wcmatch (strcase col_b) pat_mat))
              (progn (setq result col_a found T))
            )
          )
        )
      )
      (close fp)
    )
  )
  result
)

(defun EX_BuscarExpansionCode (diametro / csv_path fp line fields col_a col_b fq result found d_num)
  (setq csv_path (EX_GetCSVPath))
  (setq d_num (atof diametro) result nil found nil)
  (setq fp (open csv_path "r"))
  (if fp
    (progn
      (read-line fp)
      (while (and (not found) (setq line (EX_ReadFullCSVLine fp)))
        (setq fields (EX_ParseCSVLine line))
        (if (>= (length fields) 17)
          (progn
            (setq col_a (nth 0 fields) col_b (nth 1 fields) fq (nth 16 fields))
            (if (and (or (<= (length fields) 19) (wcmatch (strcase (nth 19 fields)) "*IN*"))
                     (or (= (atof fq) d_num) (< (abs (- (atof fq) d_num)) 0.02))
                     (or (wcmatch (strcase col_b) "*EXPANSI*N*") (wcmatch (strcase col_b) "*EXPANSION*")))
              (progn (setq result col_a found T))
            )
          )
        )
      )
      (close fp)
    )
  )
  result
)

(defun EX_BuscarTubRigidaCode (diametro material / csv_path fp line fields col_a col_b fq result found d_num pat_mat)
  (setq csv_path (EX_GetCSVPath))
  (setq d_num (atof diametro) result nil found nil)
  (setq fp (open csv_path "r"))
  (if fp
    (progn
      (setq pat_mat (if (wcmatch (strcase material) "*GALV*") "*GALV*" (strcat "*" (strcase material) "*")))
      (read-line fp)
      (while (and (not found) (setq line (EX_ReadFullCSVLine fp)))
        (setq fields (EX_ParseCSVLine line))
        (if (>= (length fields) 17)
          (progn
            (setq col_a (nth 0 fields) col_b (nth 1 fields) fq (nth 16 fields))
            (if (and (or (<= (length fields) 19) (wcmatch (strcase (nth 19 fields)) "*IN*"))
                     (or (= (atof fq) d_num) (< (abs (- (atof fq) d_num)) 0.02))
                     (wcmatch (strcase col_b) "*TUBO RIGIDO*")
                     (wcmatch (strcase col_b) pat_mat)
                     (wcmatch (strcase col_b) "*PARED GRUESA*")
                     (wcmatch (strcase col_b) "*ANILLO DE ACOPLAMIENTO*")
                     (wcmatch (strcase col_b) "*ROSCA MACHO*"))
              (progn (setq result col_a found T))
            )
          )
        )
      )
      (close fp)
    )
  )
  result
)

;; --- ANEXOS (METRICOS) ---
(defun EX_AnexoTEE (xs cr rs / rt tc)
  (setq rt (vlax-get-property xs 'Range (strcat "B" (itoa cr) ":C" (itoa cr))))
  (vlax-put-property rt 'MergeCells :vlax-true) (vl-catch-all-apply 'vlax-put-property (list rt 'HorizontalAlignment -4108)) (vlax-put-property rt 'Value2 "--- ANEXO: ACCESORIOS TEE ---")
  (vlax-put-property (vlax-get-property rt 'Interior) 'Color 13421823) (vlax-put-property (vlax-get-property rt 'Font) 'Bold :vlax-true)
  (vlax-put-property (vlax-get-property xs 'Range (strcat "B" (itoa (+ cr 1)))) 'Value2 "Total Extraido")
  (setq tc (vlax-get-property xs 'Range (strcat "C" (itoa (+ cr 1))))) (vlax-put-property tc 'Formula (strcat "=SUBTOTAL(109," rs ")"))
  (vlax-put-property (vlax-get-property xs 'Range (strcat "B" (itoa (+ cr 2)))) 'Value2 "Calculo 60% TEE")
  (setq tc (vlax-get-property xs 'Range (strcat "C" (itoa (+ cr 2))))) (vlax-put-property tc 'Formula (strcat "=ROUNDUP(C" (itoa (+ cr 1)) "*0.6,0)"))
  (vlax-put-property (vlax-get-property xs 'Range (strcat "B" (itoa (+ cr 3)))) 'Value2 "Calculo 40% TB")
  (setq tc (vlax-get-property xs 'Range (strcat "C" (itoa (+ cr 3))))) (vlax-put-property tc 'Formula (strcat "=C" (itoa (+ cr 1)) "-C" (itoa (+ cr 2))))
  (+ cr 5)
)

(defun EX_AnexoCond (xs cr rs / rt tc)
  (setq rt (vlax-get-property xs 'Range (strcat "B" (itoa cr) ":C" (itoa cr))))
  (vlax-put-property rt 'MergeCells :vlax-true) (vl-catch-all-apply 'vlax-put-property (list rt 'HorizontalAlignment -4108)) (vlax-put-property rt 'Value2 "--- ANEXO: CONDULETAS ---")
  (vlax-put-property (vlax-get-property rt 'Interior) 'Color 13421823) (vlax-put-property (vlax-get-property rt 'Font) 'Bold :vlax-true)
  (vlax-put-property (vlax-get-property xs 'Range (strcat "B" (itoa (+ cr 1)))) 'Value2 "Total Extraidas")
  (setq tc (vlax-get-property xs 'Range (strcat "C" (itoa (+ cr 1))))) (vlax-put-property tc 'Formula (strcat "=SUBTOTAL(109," rs ")"))
  (vlax-put-property (vlax-get-property xs 'Range (strcat "B" (itoa (+ cr 2)))) 'Value2 "LR (30%)")
  (setq tc (vlax-get-property xs 'Range (strcat "C" (itoa (+ cr 2))))) (vlax-put-property tc 'Formula (strcat "=ROUND(C" (itoa (+ cr 1)) "*0.3,0)"))
  (vlax-put-property (vlax-get-property xs 'Range (strcat "B" (itoa (+ cr 3)))) 'Value2 "LL (30%)")
  (setq tc (vlax-get-property xs 'Range (strcat "C" (itoa (+ cr 3))))) (vlax-put-property tc 'Formula (strcat "=ROUND(C" (itoa (+ cr 1)) "*0.3,0)"))
  (vlax-put-property (vlax-get-property xs 'Range (strcat "B" (itoa (+ cr 4)))) 'Value2 "LB (40%)")
  (setq tc (vlax-get-property xs 'Range (strcat "C" (itoa (+ cr 4))))) (vlax-put-property tc 'Formula (strcat "=C" (itoa (+ cr 1)) "-C" (itoa (+ cr 2)) "-C" (itoa (+ cr 3))))
  (+ cr 6)
)

(defun EX_AnexoPipe (xs cr rs mi / rt tc r1)
  (setq rt (vlax-get-property xs 'Range (strcat "B" (itoa cr) ":C" (itoa cr))))
  (vlax-put-property rt 'MergeCells :vlax-true) (vl-catch-all-apply 'vlax-put-property (list rt 'HorizontalAlignment -4108)) (vlax-put-property rt 'Value2 "--- ANEXO: CONDUIT ---")
  (vlax-put-property (vlax-get-property rt 'Interior) 'Color 13421823) (vlax-put-property (vlax-get-property rt 'Font) 'Bold :vlax-true)
  (setq r1 (+ cr 1))
  (vlax-put-property (vlax-get-property xs 'Range (strcat "B" (itoa r1))) 'Value2 "Total Longitud (MM)")
  (setq tc (vlax-get-property xs 'Range (strcat "C" (itoa r1)))) (vlax-put-property tc 'Formula (strcat "=SUBTOTAL(109," rs ")"))
  (vlax-put-property (vlax-get-property xs 'Range (strcat "B" (itoa (+ cr 2)))) 'Value2 "Metros Totales (MT)")
  (setq tc (vlax-get-property xs 'Range (strcat "C" (itoa (+ cr 2))))) (vlax-put-property tc 'Formula (strcat "=C" (itoa r1) "/1000"))
  (vlax-put-property (vlax-get-property xs 'Range (strcat "B" (itoa (+ cr 3)))) 'Value2 "Piezas Estimadas (3mts)")
  (setq tc (vlax-get-property xs 'Range (strcat "C" (itoa (+ cr 3))))) (vlax-put-property tc 'Formula (strcat "=ROUNDUP(C" (itoa (+ cr 2)) "/3,0)"))
  (+ cr 5)
)

(defun EX_AnexoReductores (xs cr counts / col_idx d_val rt tc)
  (setq col_idx 6 cr (1+ cr))
  (setq rt (vlax-get-property xs 'Range (strcat "E" (itoa cr) ":E" (itoa (+ cr 1)))))
  (vlax-put-property (vlax-get-property rt 'Interior) 'Color 13421823) (vlax-put-property (vlax-get-property rt 'Font) 'Bold :vlax-true)
  (vlax-put-property (vlax-get-property xs 'Range (strcat "E" (itoa cr))) 'Value2 "DIAMETRO")
  (vlax-put-property (vlax-get-property xs 'Range (strcat "E" (itoa (+ cr 1)))) 'Value2 "CANTIDAD")
  (foreach item counts
    (setq d_val (car item))
    (vlax-put-property (vlax-get-property xs 'Range (strcat (EX_GEX col_idx) (itoa cr))) 'Value2 d_val)
    (vlax-put-property (vlax-get-property xs 'Range (strcat (EX_GEX col_idx) (itoa (+ cr 1)))) 'Value2 (cdr item))
    (setq col_idx (1+ col_idx))
  )
  (setq tc (vlax-get-property xs 'Range (strcat "E" (itoa (1- cr)) ":" (EX_GEX (1- col_idx)) (itoa (1- cr)))))
  (vlax-put-property tc 'MergeCells :vlax-true) (vl-catch-all-apply 'vlax-put-property (list tc 'HorizontalAlignment -4108)) (vlax-put-property tc 'Value2 "--- ANEXO: REDUCCIONES ---") (vlax-put-property (vlax-get-property tc 'Font) 'Bold :vlax-true) (vlax-put-property (vlax-get-property tc 'Interior) 'Color 13421823)
  cr
)

(defun EX_AnexoTipos (xs cr counts forma mat / col_idx d_val total t_lr t_ll t_lb dec_dia rt tc tipo_pair)
  (setq col_idx 6 cr (1+ cr)) ;; Column E for labels, F+ for data
  (setq rt (vlax-get-property xs 'Range (strcat "E" (itoa cr) ":E" (itoa (+ cr 2)))))
  (vlax-put-property (vlax-get-property rt 'Interior) 'Color 13421823) (vlax-put-property (vlax-get-property rt 'Font) 'Bold :vlax-true)
  (vlax-put-property (vlax-get-property xs 'Range (strcat "E" (itoa cr))) 'Value2 "TIPO")
  (vlax-put-property (vlax-get-property xs 'Range (strcat "E" (itoa (+ cr 1)))) 'Value2 "CANTIDAD")
  (vlax-put-property (vlax-get-property xs 'Range (strcat "E" (itoa (+ cr 2)))) 'Value2 "CODIGO TIPO")
  (foreach item counts
    (setq d_val (car item) total (cdr item))
    (setq t_lr (fix (+ (* total 0.3) 0.5)) t_ll (fix (+ (* total 0.3) 0.5)) t_lb (- total t_lr t_ll))
    (setq dec_dia (EX_DiametroDecimal d_val))
    (foreach tipo_pair (list (cons "LR" t_lr) (cons "LL" t_ll) (cons "LB" t_lb))
      (if (> (cdr tipo_pair) 0)
        (progn
          (vlax-put-property (vlax-get-property xs 'Range (strcat (EX_GEX col_idx) (itoa cr))) 'Value2 (strcat (car tipo_pair) " (" d_val ")"))
          (vlax-put-property (vlax-get-property xs 'Range (strcat (EX_GEX col_idx) (itoa (+ cr 1)))) 'Value2 (cdr tipo_pair))
          (vlax-put-property (vlax-get-property xs 'Range (strcat (EX_GEX col_idx) (itoa (+ cr 2)))) 'Value2 (EX_BuscarDentCode dec_dia forma mat "IN" (car tipo_pair)))
          (setq col_idx (1+ col_idx))
        )
      )
    )
  )
  (setq tc (vlax-get-property xs 'Range (strcat "E" (itoa (1- cr)) ":" (EX_GEX (1- col_idx)) (itoa (1- cr)))))
  (vlax-put-property tc 'MergeCells :vlax-true) (vl-catch-all-apply 'vlax-put-property (list tc 'HorizontalAlignment -4108)) (vlax-put-property tc 'Value2 "--- ANEXO: TIPO CONDULETAS ---") (vlax-put-property (vlax-get-property tc 'Font) 'Bold :vlax-true) (vlax-put-property (vlax-get-property tc 'Interior) 'Color 13421823)
  (+ cr 6)
)

(defun EX_AnexoCondC (xs cr counts forma mat / col_idx d_val sum_in pz dec_dia rt tc)
  (setq col_idx 6 cr (1+ cr)) ;; Column E for labels, F+ for data
  (setq rt (vlax-get-property xs 'Range (strcat "E" (itoa cr) ":E" (itoa (+ cr 3)))))
  (vlax-put-property (vlax-get-property rt 'Interior) 'Color 13421823) (vlax-put-property (vlax-get-property rt 'Font) 'Bold :vlax-true)
  (vlax-put-property (vlax-get-property xs 'Range (strcat "E" (itoa cr))) 'Value2 "DIAMETRO")
  (vlax-put-property (vlax-get-property xs 'Range (strcat "E" (itoa (+ cr 1)))) 'Value2 "CANTIDAD")
  (vlax-put-property (vlax-get-property xs 'Range (strcat "E" (itoa (+ cr 2)))) 'Value2 "CODIGO TIPO")
  (vlax-put-property (vlax-get-property xs 'Range (strcat "E" (itoa (+ cr 3)))) 'Value2 "CODIGO UNION")
  (foreach item counts
    (setq d_val (car item) sum_in (cdr item) pz (fix (+ (/ (/ sum_in 1000.0) 9.0) 0.999999)) dec_dia (EX_DiametroDecimal d_val))
    (vlax-put-property (vlax-get-property xs 'Range (strcat (EX_GEX col_idx) (itoa cr))) 'Value2 d_val)
    (vlax-put-property (vlax-get-property xs 'Range (strcat (EX_GEX col_idx) (itoa (+ cr 1)))) 'Value2 pz)
    (vlax-put-property (vlax-get-property xs 'Range (strcat (EX_GEX col_idx) (itoa (+ cr 2)))) 'Value2 (EX_BuscarDentCode dec_dia forma mat "IN" "C"))
    (vlax-put-property (vlax-get-property xs 'Range (strcat (EX_GEX col_idx) (itoa (+ cr 3)))) 'Value2 (EX_BuscarUnionCode dec_dia mat))
    (setq col_idx (1+ col_idx))
  )
  (setq tc (vlax-get-property xs 'Range (strcat "E" (itoa (1- cr)) ":" (EX_GEX (1- col_idx)) (itoa (1- cr)))))
  (vlax-put-property tc 'MergeCells :vlax-true) (vl-catch-all-apply 'vlax-put-property (list tc 'HorizontalAlignment -4108)) (vlax-put-property tc 'Value2 "--- ANEXO: CONDULETA TIPO C Y UNION ---") (vlax-put-property (vlax-get-property tc 'Font) 'Bold :vlax-true) (vlax-put-property (vlax-get-property tc 'Interior) 'Color 13421823)
  (+ cr 5)
)

(defun EX_AnexoTEEDetalle (xs cr counts forma mat / col_idx d_val d_cnt dec_dia rt tc cnt_tb cnt_t t_counts tb_counts)
  (setq t_counts '() tb_counts '())
  (foreach item counts
    (setq d_val (car item) d_cnt (cdr item))
    (setq cnt_tb (fix (+ (* d_cnt 0.4) 0.5)))
    (setq cnt_t (- d_cnt cnt_tb))
    (if (> cnt_t 0) (setq t_counts (cons (cons d_val cnt_t) t_counts)))
    (if (> cnt_tb 0) (setq tb_counts (cons (cons d_val cnt_tb) tb_counts)))
  )
  (setq t_counts (reverse t_counts) tb_counts (reverse tb_counts))
  (if t_counts
    (progn
      (setq col_idx 6 cr (1+ cr)) ;; Column E for labels
      (setq rt (vlax-get-property xs 'Range (strcat "E" (itoa cr) ":E" (itoa (+ cr 2)))))
      (vlax-put-property (vlax-get-property rt 'Interior) 'Color 13421823) (vlax-put-property (vlax-get-property rt 'Font) 'Bold :vlax-true)
      (vlax-put-property (vlax-get-property xs 'Range (strcat "E" (itoa cr))) 'Value2 "DIAMETRO")
      (vlax-put-property (vlax-get-property xs 'Range (strcat "E" (itoa (+ cr 1)))) 'Value2 "CANTIDAD")
      (vlax-put-property (vlax-get-property xs 'Range (strcat "E" (itoa (+ cr 2)))) 'Value2 "CODIGO TIPO")
      (foreach item t_counts
        (setq d_val (car item) d_cnt (cdr item) dec_dia (EX_DiametroDecimal d_val))
        (vlax-put-property (vlax-get-property xs 'Range (strcat (EX_GEX col_idx) (itoa cr))) 'Value2 d_val)
        (vlax-put-property (vlax-get-property xs 'Range (strcat (EX_GEX col_idx) (itoa (+ cr 1)))) 'Value2 d_cnt)
        (vlax-put-property (vlax-get-property xs 'Range (strcat (EX_GEX col_idx) (itoa (+ cr 2)))) 'Value2 (EX_BuscarDentCode dec_dia forma mat "IN" "T"))
        (setq col_idx (1+ col_idx))
      )
      (setq tc (vlax-get-property xs 'Range (strcat "E" (itoa (1- cr)) ":" (EX_GEX (1- col_idx)) (itoa (1- cr)))))
      (vlax-put-property tc 'MergeCells :vlax-true) (vl-catch-all-apply 'vlax-put-property (list tc 'HorizontalAlignment -4108)) (vlax-put-property tc 'Value2 "--- ANEXO: TIPO CONDULETAS TIPO T ---") (vlax-put-property (vlax-get-property tc 'Font) 'Bold :vlax-true) (vlax-put-property (vlax-get-property tc 'Interior) 'Color 13421823)
      (setq cr (+ cr 5))
    )
  )
  (if tb_counts
    (progn
      (setq col_idx 6 cr (1+ cr))
      (setq rt (vlax-get-property xs 'Range (strcat "E" (itoa cr) ":E" (itoa (+ cr 2)))))
      (vlax-put-property (vlax-get-property rt 'Interior) 'Color 13421823) (vlax-put-property (vlax-get-property rt 'Font) 'Bold :vlax-true)
      (vlax-put-property (vlax-get-property xs 'Range (strcat "E" (itoa cr))) 'Value2 "DIAMETRO")
      (vlax-put-property (vlax-get-property xs 'Range (strcat "E" (itoa (+ cr 1)))) 'Value2 "CANTIDAD")
      (vlax-put-property (vlax-get-property xs 'Range (strcat "E" (itoa (+ cr 2)))) 'Value2 "CODIGO TIPO")
      (foreach item tb_counts
        (setq d_val (car item) d_cnt (cdr item) dec_dia (EX_DiametroDecimal d_val))
        (vlax-put-property (vlax-get-property xs 'Range (strcat (EX_GEX col_idx) (itoa cr))) 'Value2 d_val)
        (vlax-put-property (vlax-get-property xs 'Range (strcat (EX_GEX col_idx) (itoa (+ cr 1)))) 'Value2 d_cnt)
        (vlax-put-property (vlax-get-property xs 'Range (strcat (EX_GEX col_idx) (itoa (+ cr 2)))) 'Value2 (EX_BuscarDentCode dec_dia forma mat "IN" "TB"))
        (setq col_idx (1+ col_idx))
      )
      (setq tc (vlax-get-property xs 'Range (strcat "E" (itoa (1- cr)) ":" (EX_GEX (1- col_idx)) (itoa (1- cr)))))
      (vlax-put-property tc 'MergeCells :vlax-true) (vl-catch-all-apply 'vlax-put-property (list tc 'HorizontalAlignment -4108)) (vlax-put-property tc 'Value2 "--- ANEXO: TIPO CONDULETAS TIPO TB ---") (vlax-put-property (vlax-get-property tc 'Font) 'Bold :vlax-true) (vlax-put-property (vlax-get-property tc 'Interior) 'Color 13421823)
      (setq cr (+ cr 5))
    )
  )
  cr
)

(defun EX_AnexoTapasEmpacaduras (xs cr counts forma mat / col_idx d_val d_cnt dec_dia rt tc cod_t cod_e sorted_counts)
  (setq sorted_counts (vl-sort counts (function (lambda (a b) (< (atof (EX_DiametroDecimal (car a))) (atof (EX_DiametroDecimal (car b))))))))
  (setq col_idx 6 cr (1+ cr)) ;; Column E for labels
  (setq rt (vlax-get-property xs 'Range (strcat "E" (itoa cr) ":E" (itoa (+ cr 3)))))
  (vlax-put-property (vlax-get-property rt 'Interior) 'Color 13421823) (vlax-put-property (vlax-get-property rt 'Font) 'Bold :vlax-true)
  (vlax-put-property (vlax-get-property rt 'Font) 'Color 0)
  (vlax-put-property (vlax-get-property xs 'Range (strcat "E" (itoa cr))) 'Value2 "DIAMETRO")
  (vlax-put-property (vlax-get-property xs 'Range (strcat "E" (itoa (+ cr 1)))) 'Value2 "CANTIDAD")
  (vlax-put-property (vlax-get-property xs 'Range (strcat "E" (itoa (+ cr 2)))) 'Value2 "CODIGO TAPA")
  (vlax-put-property (vlax-get-property xs 'Range (strcat "E" (itoa (+ cr 3)))) 'Value2 "CODIGO EMPACADURA")
  (foreach item sorted_counts
    (setq d_val (car item) d_cnt (cdr item) dec_dia (EX_DiametroDecimal d_val) cod_t (EX_BuscarTapaCode dec_dia forma mat) cod_e (EX_BuscarEmpaCode dec_dia forma mat))
    (vlax-put-property (vlax-get-property xs 'Range (strcat (EX_GEX col_idx) (itoa cr))) 'Value2 d_val)
    (vlax-put-property (vlax-get-property xs 'Range (strcat (EX_GEX col_idx) (itoa (+ cr 1)))) 'Value2 (fix d_cnt))
    (setq tc (vlax-get-property xs 'Range (strcat (EX_GEX col_idx) (itoa (+ cr 2)))))
    (if cod_t (vlax-put-property tc 'Value2 cod_t))
    (setq tc (vlax-get-property xs 'Range (strcat (EX_GEX col_idx) (itoa (+ cr 3)))))
    (if cod_e (vlax-put-property tc 'Value2 cod_e))
    (setq col_idx (1+ col_idx))
  )
  (setq tc (vlax-get-property xs 'Range (strcat "E" (itoa (1- cr)) ":" (EX_GEX (1- col_idx)) (itoa (1- cr)))))
  (vlax-put-property tc 'MergeCells :vlax-true) (vl-catch-all-apply 'vlax-put-property (list tc 'HorizontalAlignment -4108))
  (vlax-put-property tc 'Value2 "--- ANEXO: TAPAS Y EMPACADURAS ---") (vlax-put-property (vlax-get-property tc 'Font) 'Bold :vlax-true) (vlax-put-property (vlax-get-property tc 'Interior) 'Color 13421823)
  (+ cr 5)
)

(defun EX_AnexoExpansion (xs cr counts forma mat / col_idx d_val sum_in pz dec_dia rt tc)
  (setq col_idx 6 cr (1+ cr))
  (setq rt (vlax-get-property xs 'Range (strcat "E" (itoa cr) ":E" (itoa (+ cr 2)))))
  (vlax-put-property (vlax-get-property rt 'Interior) 'Color 13421823) (vlax-put-property (vlax-get-property rt 'Font) 'Bold :vlax-true)
  (vlax-put-property (vlax-get-property xs 'Range (strcat "E" (itoa cr))) 'Value2 "DIAMETRO")
  (vlax-put-property (vlax-get-property xs 'Range (strcat "E" (itoa (+ cr 1)))) 'Value2 "CANTIDAD")
  (vlax-put-property (vlax-get-property xs 'Range (strcat "E" (itoa (+ cr 2)))) 'Value2 "CODIGO JUNTA EXP.")
  (foreach item counts
    (setq d_val (car item) sum_in (cdr item) pz (fix (+ (/ (/ sum_in 1000.0) 27.0) 0.999999)) dec_dia (EX_DiametroDecimal d_val))
    (vlax-put-property (vlax-get-property xs 'Range (strcat (EX_GEX col_idx) (itoa cr))) 'Value2 d_val)
    (vlax-put-property (vlax-get-property xs 'Range (strcat (EX_GEX col_idx) (itoa (+ cr 1)))) 'Value2 pz)
    (vlax-put-property (vlax-get-property xs 'Range (strcat (EX_GEX col_idx) (itoa (+ cr 2)))) 'Value2 (EX_BuscarExpansionCode dec_dia))
    (setq col_idx (1+ col_idx))
  )
  (setq tc (vlax-get-property xs 'Range (strcat "E" (itoa (1- cr)) ":" (EX_GEX (1- col_idx)) (itoa (1- cr)))))
  (vlax-put-property tc 'MergeCells :vlax-true) (vl-catch-all-apply 'vlax-put-property (list tc 'HorizontalAlignment -4108)) (vlax-put-property tc 'Value2 "--- ANEXO: JUNTAS DE EXPANCION ---") (vlax-put-property (vlax-get-property tc 'Font) 'Bold :vlax-true) (vlax-put-property (vlax-get-property tc 'Interior) 'Color 13421823)
  (+ cr 5)
)

(defun EX_AnexoTuberiaRigida (xs cr counts mat / col_idx d_val sum_in pz dec_dia rt tc)
  (setq col_idx 6 cr (1+ cr))
  (setq rt (vlax-get-property xs 'Range (strcat "E" (itoa cr) ":E" (itoa (+ cr 2)))))
  (vlax-put-property (vlax-get-property rt 'Interior) 'Color 13421823) (vlax-put-property (vlax-get-property rt 'Font) 'Bold :vlax-true)
  (vlax-put-property (vlax-get-property xs 'Range (strcat "E" (itoa cr))) 'Value2 "DIAMETRO")
  (vlax-put-property (vlax-get-property xs 'Range (strcat "E" (itoa (+ cr 1)))) 'Value2 "PIEZAS")
  (vlax-put-property (vlax-get-property xs 'Range (strcat "E" (itoa (+ cr 2)))) 'Value2 "CODIGO TUB. RIGIDA")
  (foreach item counts
    (setq d_val (car item) sum_in (cdr item) pz (fix (+ (/ (/ sum_in 1000.0) 3.0) 0.999999)) dec_dia (EX_DiametroDecimal d_val))
    (vlax-put-property (vlax-get-property xs 'Range (strcat (EX_GEX col_idx) (itoa cr))) 'Value2 d_val)
    (vlax-put-property (vlax-get-property xs 'Range (strcat (EX_GEX col_idx) (itoa (+ cr 1)))) 'Value2 pz)
    (vlax-put-property (vlax-get-property xs 'Range (strcat (EX_GEX col_idx) (itoa (+ cr 2)))) 'Value2 (EX_BuscarTubRigidaCode dec_dia mat))
    (setq col_idx (1+ col_idx))
  )
  (setq tc (vlax-get-property xs 'Range (strcat "E" (itoa (1- cr)) ":" (EX_GEX (1- col_idx)) (itoa (1- cr)))))
  (vlax-put-property tc 'MergeCells :vlax-true) (vl-catch-all-apply 'vlax-put-property (list tc 'HorizontalAlignment -4108)) (vlax-put-property tc 'Value2 "--- ANEXO: TUBERIA RIGIDA ---") (vlax-put-property (vlax-get-property tc 'Font) 'Bold :vlax-true) (vlax-put-property (vlax-get-property tc 'Interior) 'Color 13421823)
  (+ cr 5)
)

(defun EX_BuscarReductorCode (dia1 dia2 / csv_path fp line fields col_a col_b fq ft result found d_num1 d_num2)
  (setq csv_path (EX_GetCSVPath))
  (setq d_num1 (atof dia1) d_num2 (atof dia2) result nil found nil)
  (setq fp (open csv_path "r"))
  (if fp
    (progn
      (read-line fp)
      (while (and (not found) (setq line (EX_ReadFullCSVLine fp)))
        (setq fields (EX_ParseCSVLine line))
        (if (>= (length fields) 18)
          (progn
            (setq col_a (nth 0 fields) col_b (nth 1 fields) fq (nth 16 fields) ft (nth 17 fields))
            (if (and (or (<= (length fields) 19) (wcmatch (strcase (nth 19 fields)) "*IN*"))
                     (or (= (atof fq) d_num1) (< (abs (- (atof fq) d_num1)) 0.02))
                     (or (= (atof ft) d_num2) (< (abs (- (atof ft) d_num2)) 0.02))
                     (wcmatch (strcase col_b) "*ACOPLE*REDUCTOR*"))
              (progn (setq result col_a found T))
            )
          )
        )
      )
      (close fp)
    )
  )
  result
)

(defun EX_AnexoReductores (xs cr counts / col_idx d1 d2 d1_fmt d2_fmt rt tc codigo it header_range sorted_counts)
  (if (and counts (> (length counts) 0))
    (progn
      ;; Sort counts by dia1 desc, then dia2 desc
      (setq sorted_counts (vl-sort counts 
        (function (lambda (a b) 
          (if (/= (atof (caar a)) (atof (caar b)))
            (> (atof (caar a)) (atof (caar b)))
            (> (atof (cdar a)) (atof (cdar b)))
          )
        ))
      ))
      (setq col_idx 6 cr (1+ cr)) ;; Column E for labels
      (setq rt (vlax-get-property xs 'Range (strcat "E" (itoa cr) ":E" (itoa (+ cr 2)))))
      (vlax-put-property (vlax-get-property rt 'Interior) 'Color 13421823)
      (vlax-put-property (vlax-get-property rt 'Font) 'Bold :vlax-true)
      (vlax-put-property (vlax-get-property rt 'Font) 'Color 0)
      (vlax-put-property (vlax-get-property xs 'Range (strcat "E" (itoa cr))) 'Value2 "MEDIDA")
      (vlax-put-property (vlax-get-property xs 'Range (strcat "E" (itoa (+ cr 1)))) 'Value2 "CANTIDAD")
      (vlax-put-property (vlax-get-property xs 'Range (strcat "E" (itoa (+ cr 2)))) 'Value2 "CODIGO SPM")
      
      (foreach it sorted_counts
        (setq d1 (caar it) d2 (cdar it) cnt (cdr it))
        (setq d1_fmt (EX_FormatearFraccion d1) d2_fmt (EX_FormatearFraccion d2))
        (setq codigo (EX_BuscarReductorCode d1 d2))
        (setq tc (vlax-get-property xs 'Range (strcat (EX_GEX col_idx) (itoa cr))))
        (vlax-put-property tc 'Value2 (strcat d1_fmt " A " d2_fmt))
        (setq tc (vlax-get-property xs 'Range (strcat (EX_GEX col_idx) (itoa (+ cr 1)))))
        (vlax-put-property tc 'Value2 cnt)
        (setq tc (vlax-get-property xs 'Range (strcat (EX_GEX col_idx) (itoa (+ cr 2)))))
        (vlax-put-property tc 'Value2 (if codigo codigo "N/A"))
        (setq col_idx (1+ col_idx))
      )
      
      (setq header_range (vlax-get-property xs 'Range (strcat "E" (itoa (1- cr)) ":" (EX_GEX (1- col_idx)) (itoa (1- cr)))))
      (vlax-put-property header_range 'MergeCells :vlax-true)
      (vlax-put-property header_range 'Value2 "--- ANEXO: REDUCCIONES ---")
      (vlax-put-property (vlax-get-property header_range 'Font) 'Bold :vlax-true)
      (vlax-put-property (vlax-get-property header_range 'Interior) 'Color 13421823)
      (vl-catch-all-apply 'vlax-put-property (list header_range 'HorizontalAlignment -4108))
      (setq cr (+ cr 5))
    )
  )
  cr
)

;; --- COMANDO PRINCIPAL ---
(defun c:EXCEL_PRO ( / ss i e o n bl current df f id rs sb q c40 c41 xa xb xs r c t_s ty b_n b_o t_g v_l c_i er mi hm ft fc cr h tc ra pz ap range_str spm_col tipo_col dia_val dent_code *forma_idx* *mat_idx* desc_tee cond_counts tee_detailed_counts cond_assigned d_val it_c target_lr target_ll current_lr current_ll current_ll assigned_tipo pipe_sums tcm item_p start_cr start_cr_pipe reductor_counts)
  (princ "\n--- EXCEL PRO v9.8.2 MM ---")
  (if (not *forma_sel*) (setq *forma_sel* "7"))
  (if (not *mat_sel*)   (setq *mat_sel* "Acero Galvanizado"))
  (setq ss (ssget "X" '((0 . "INSERT") (410 . "Model"))))
  (if (not ss) (progn (alert "No hay bloques.") (exit)))
  
  (setq bl '() i 0 q (chr 34) c40 (chr 40) c41 (chr 41))
  (repeat (sslength ss) (setq e (ssname ss i) o (vlax-ename->vla-object e) n (vl-catch-all-apply 'vla-get-EffectiveName (list o))) (if (vl-catch-all-error-p n) (setq n (vla-get-Name o))) (setq n (vl-princ-to-string n)) (if (not (assoc n bl)) (setq bl (cons (cons n 0) bl))) (setq i (1+ i)))
  
  (setq current bl df (strcat (if (getvar "TEMPPREFIX") (getvar "TEMPPREFIX") "C:/Temp/") "ex_mm.dcl") f (open df "w"))
  (write-line (strcat "ex : dialog { label=" q "Excel Pro MM v8.5" q "; :column { :edit_box { key=" q "f" q "; label=" q "Filtro:" q "; } :list_box { key=" q "l" q "; multiple_select=true; height=20; width=55; } } :row { :popup_list { key=" q "forma" q "; label=" q "Forma:" q "; width=20; } :popup_list { key=" q "material" q "; label=" q "Material:" q "; width=30; } } :row { :button { key=" q "accept" q "; label=" q "GENERAR" q "; is_default=true; } :button { key=" q "cancel" q "; label=" q "Cerrar" q "; is_cancel=true; } } }") f) (close f)
  
  (defun ULV () (start_list "l") (foreach x current (add_list (strcat (if (= (cdr x) 1) "[X] " "[ ] ") (car x)))) (end_list))
  (defun UF (v / s) (setq s (strcase v) current '()) (foreach x bl (if (wcmatch (strcase (car x)) (strcat "*" s "*")) (setq current (append current (list x))))) (ULV))
  (defun TS (v / idx bn os ns cm it) (setq cm (strcat c40 v c41) idx (read cm)) (foreach i idx (setq bn (car (nth i current)) it (assoc bn bl) os (cdr it) ns (if (= os 1) 0 1) bl (subst (cons bn ns) it bl) current (subst (cons bn ns) (nth i current) current))) (ULV))
  
  (setq id (load_dialog df))
  (if (and id (new_dialog "ex" id))
    (progn (ULV) 
      (start_list "forma") (add_list "7") (add_list "8") (end_list)
      (setq *forma_idx* (if (= *forma_sel* "8") "1" "0"))
      (set_tile "forma" *forma_idx*)
      (start_list "material") (add_list "Acero Galvanizado") (add_list "Aluminio") (end_list)
      (setq *mat_idx* (if (= *mat_sel* "Aluminio") "1" "0"))
      (set_tile "material" *mat_idx*)
      (action_tile "f" "(UF $value)") (action_tile "l" "(TS $value)") 
      (action_tile "forma"    "(setq *forma_idx* $value)")
      (action_tile "material" "(setq *mat_idx* $value)")
      (action_tile "accept" "(progn (setq *forma_sel* (if (= *forma_idx* \"1\") \"8\" \"7\")) (setq *mat_sel* (if (= *mat_idx* \"1\") \"Aluminio\" \"Acero Galvanizado\")) (done_dialog 1))")
      (action_tile "cancel" "(done_dialog 0)") (setq rs (start_dialog)) (unload_dialog id)
      (if (= rs 1)
        (progn (setq sb '()) (foreach x bl (if (= (cdr x) 1) (setq sb (cons (car x) sb))))
          (if sb 
            (progn (setq mi 53 t_s '("BLOQUE") ty '() i 0 hm nil ft 0.0 fc 0.0 pipe_sums '() tee_detailed_counts '() reductor_counts '())
              (repeat (sslength ss) (setq e (ssname ss i) o (vlax-ename->vla-object e) n (vl-princ-to-string (vl-catch-all-apply 'vla-get-EffectiveName (list o)))) (if (and (member n sb) (not (member n ty))) (setq ty (append ty (list n)))) (setq i (1+ i)))
              (foreach b_n ty (setq b_o (EX_GBO b_n)) (foreach t_g b_o (if (not (member t_g t_s)) (setq t_s (append t_s (list t_g))))))
              
              (setq t_s_final '())
              (foreach h t_s
                (if (member (strcase h) '("LONGITUD" "L" "LEN" "LENGTH" "LONG"))
                  (setq t_s_final (append t_s_final (list "LONGITUD (MM)" "LONGITUD (MT)")))
                  (setq t_s_final (append t_s_final (list h)))
                )
              )
              (setq t_s t_s_final)

              (setq cond_counts '() i 0)
              (repeat (sslength ss)
                (setq e (ssname ss i) o (vlax-ename->vla-object e) n (vl-princ-to-string (vl-catch-all-apply 'vla-get-EffectiveName (list o))))
                (if (and (member n sb) (wcmatch (strcase n) "CONDULETA_*") (not (wcmatch (strcase n) "CONDULETA_TIPO_*")))
                  (progn
                    (setq d_val nil)
                    (if (and (vlax-property-available-p o 'HasAttributes) (= (vla-get-HasAttributes o) :vlax-true))
                      (foreach at (vlax-invoke o 'GetAttributes)
                        (if (member (strcase (vla-get-TagString at)) '("DIAMETRO" "DIAM" "D" "DIA" "INPUT_1")) (setq d_val (vla-get-TextString at)))))
                    (if (not d_val) (foreach co (EX_GCA n) (if (member (strcase (car co)) '("DIAMETRO" "DIAM" "D" "DIA" "INPUT_1")) (setq d_val (cdr co)))))
                    (if d_val
                      (progn
                        (setq it_c (assoc d_val cond_counts))
                        (if it_c (setq cond_counts (subst (cons d_val (1+ (cdr it_c))) it_c cond_counts)) (setq cond_counts (cons (cons d_val 1) cond_counts)))))))
                (if (and (member n sb) (wcmatch (strcase n) "CONDULETA_TIPO_TEE*"))
                  (progn
                    (setq d_val nil)
                    (if (and (vlax-property-available-p o 'HasAttributes) (= (vla-get-HasAttributes o) :vlax-true))
                      (foreach at (vlax-invoke o 'GetAttributes)
                        (if (member (strcase (vla-get-TagString at)) '("DIAMETRO" "DIAM" "D" "DIA" "INPUT_1")) (setq d_val (vla-get-TextString at)))))
                    (if (not d_val) (foreach co (EX_GCA n) (if (member (strcase (car co)) '("DIAMETRO" "DIAM" "D" "DIA" "INPUT_1")) (setq d_val (cdr co)))))
                    (if d_val
                      (progn
                        (setq it_t (assoc d_val tee_detailed_counts))
                        (if it_t (setq tee_detailed_counts (subst (cons d_val (1+ (cdr it_t))) it_t tee_detailed_counts)) (setq tee_detailed_counts (cons (cons d_val 1) tee_detailed_counts)))))))
                (setq i (1+ i)))
              (setq cond_assigned '())
              
              (setq t_s (append t_s (list "TIPO" "Codigo SPM")))
              (setq spm_col (length t_s) tipo_col (1- spm_col))
              (setq xa (vlax-get-or-create-object "Excel.Application")) (vlax-put-property xa 'Visible :vlax-true) (setq xb (vlax-invoke-method (vlax-get-property xa 'Workbooks) 'Add) xs (vlax-get-property xb 'ActiveSheet))
              (setq c 1) (foreach h t_s (setq tc (vlax-get-property xs 'Range (strcat (EX_GEX c) "1"))) (vlax-put-property tc 'Value2 h) (vlax-put-property (vlax-get-property tc 'Interior) 'Color 6299648) (vlax-put-property (vlax-get-property tc 'Font) 'Color 16777215) (vlax-put-property (vlax-get-property tc 'Font) 'Bold :vlax-true) (setq c (1+ c)))
              (setq r 2 i 0)
              (repeat (sslength ss) 
                (setq e (ssname ss i) o (vlax-ename->vla-object e) n (vl-princ-to-string (vl-catch-all-apply 'vla-get-EffectiveName (list o))))
                (if (member n sb) 
                  (progn 
                    (vl-catch-all-apply 'vlax-put-property (list (vlax-get-property xs 'Range (strcat "A" (itoa r))) 'Value2 n))
                    (setq ra '() pz 1.0 dia_val nil) 
                    (if (and (vlax-property-available-p o 'HasAttributes) (= (vla-get-HasAttributes o) :vlax-true)) 
                      (foreach at (vlax-invoke o 'GetAttributes) (setq ra (cons (cons (vla-get-TagString at) (vla-get-TextString at)) ra)))
                    )
                    (foreach co (EX_GCA n) (setq ra (cons co ra)))
                    (foreach ap ra (if (and (not dia_val) (member (strcase (car ap)) '("DIAMETRO" "DIAM" "D" "DIA" "INPUT_1"))) (setq dia_val (cdr ap))))
                    
                    (foreach ap ra 
                      (setq t_g (car ap) v_l (cdr ap))
                      (setq c_i (if (member (strcase t_g) '("LONGITUD" "L" "LEN" "LENGTH" "LONG")) 
                                     (vl-position "LONGITUD (MM)" t_s)
                                     (vl-position t_g t_s)))
                      (if (and c_i (member (strcase t_g) '("PZ" "PZS" "CANT" "QTY" "CANTIDAD"))) 
                        (setq pz (if (and v_l (/= v_l "")) (distof v_l) 1.0))
                      )
                      (if c_i 
                        (progn 
                          (setq er (EX_PIB t_g v_l) tc (vlax-get-property xs 'Range (strcat (EX_GEX (1+ c_i)) (itoa r)))) 
                          (if (not (vl-catch-all-error-p er)) 
                            (cond 
                              ((= (car er) "TXT") (vlax-put-property tc 'Value2 (cadr er))) 
                              ((= (car er) "NUM") (vlax-put-property tc 'Value2 (cadr er))) 
                              ((= (car er) "RAW") (vlax-put-property tc 'Value2 (cadr er))) 
                                ((= (car er) "WMM") 
                                  (vlax-put-property tc 'Value2 (caddr er)) 
                                  (setq tcm (vlax-get-property xs 'Range (strcat (EX_GEX (+ 2 c_i)) (itoa r))))
                                  (vlax-put-property tcm 'Value2 (/ (caddr er) 1000.0))
                                  (vlax-put-property (vlax-get-property xs 'Range (strcat (EX_GEX mi) (itoa r))) 'Value2 (caddr er)) 
                                  (setq hm T)
                                  (if (and dia_val (wcmatch (strcase n) "CONDUIT_*"))
                                    (progn
                                      (setq item_p (assoc dia_val pipe_sums))
                                      (if item_p 
                                        (setq pipe_sums (subst (cons dia_val (+ (cdr item_p) (caddr er))) item_p pipe_sums))
                                        (setq pipe_sums (cons (cons dia_val (caddr er)) pipe_sums))
                                      )
                                    )
                                  )
                                )
                            )
                          )
                        )
                      )
                    )
                    (if (wcmatch (strcase n) "*CONDULETA_TIPO_TEE*")
                        (progn (vlax-put-property (vlax-get-property xs 'Range (strcat (EX_GEX 54) (itoa r))) 'Value2 pz) (setq ft (+ ft pz)))
                        (if (or (wcmatch (strcase n) "*CONDULETA*") (wcmatch (strcase n) "*LL*") (wcmatch (strcase n) "*LB*") (wcmatch (strcase n) "*LR*"))
                            (progn (vlax-put-property (vlax-get-property xs 'Range (strcat (EX_GEX 55) (itoa r))) 'Value2 pz) (setq fc (+ fc pz)))
                        )
                    )
                    (if (and dia_val (or (wcmatch (strcase n) "*CONDULETA*") (wcmatch (strcase n) "*LL*") (wcmatch (strcase n) "*LB*") (wcmatch (strcase n) "*LR*")))
                      (progn
                        (setq i_red 1)
                        (while (<= i_red 3)
                          (setq t_medida (strcat "*REDUC*" (itoa i_red) "*"))
                          (setq t_cant   (strcat "*CANT*" (itoa i_red) "*"))
                          (setq v_medida nil v_cant 0)
                          (foreach ap ra
                            (if (wcmatch (strcase (car ap)) t_medida) (setq v_medida (cdr ap)))
                            (if (wcmatch (strcase (car ap)) t_cant) (setq v_cant (if (and (cdr ap) (/= (cdr ap) "")) (atoi (cdr ap)) 0)))
                          )
                          (if (and v_medida (/= v_medida "") (/= v_medida "0") (not (wcmatch (strcase v_medida) "*N/A*")) (> v_cant 0))
                            (progn
                              (setq dia1_dec (EX_DiametroDecimal dia_val))
                              (setq dia2_dec (EX_DiametroDecimal v_medida))
                              (if (and dia1_dec dia2_dec)
                                (progn
                                  (setq red_pair (cons dia1_dec dia2_dec))
                                  (setq it_r (assoc red_pair reductor_counts))
                                  (if it_r
                                    (setq reductor_counts (subst (cons red_pair (+ (cdr it_r) v_cant)) it_r reductor_counts))
                                    (setq reductor_counts (cons (cons red_pair v_cant) reductor_counts))
                                  )
                                )
                              )
                            )
                          )
                          (setq i_red (1+ i_red))
                        )
                      )
                    )
                    (if (and dia_val (/= dia_val ""))
                      (progn
                        (setq *ultima_desc* nil assigned_tipo nil dent_code nil)
                        (cond 
                          ((wcmatch (strcase n) "CONDUIT_*")
                           (setq dent_code (EX_BuscarTubRigidaCode (EX_DiametroDecimal dia_val) *mat_sel*)))
                          ((wcmatch (strcase n) "*CONDULETA_TIPO_TEE*")
                           (setq assigned_tipo "T"))
                          ((and (wcmatch (strcase n) "CONDULETA_*") (not (wcmatch (strcase n) "CONDULETA_TIPO_*")))
                           (setq it_c (assoc dia_val cond_counts) it_a (assoc dia_val cond_assigned))
                           (if (not it_a) (setq it_a (cons dia_val 0) cond_assigned (cons it_a cond_assigned)))
                           (setq target_lr (fix (+ (* (cdr it_c) 0.3) 0.5))
                                 target_ll (fix (+ (* (cdr it_c) 0.3) 0.5))
                                 current_assigned (cdr it_a))
                           (cond 
                             ((< current_assigned target_lr) (setq assigned_tipo "LR"))
                             ((< current_assigned (+ target_lr target_ll)) (setq assigned_tipo "LL"))
                             (t (setq assigned_tipo "LB"))
                           )
                           (setq cond_assigned (subst (cons dia_val (1+ current_assigned)) it_a cond_assigned))
                           (vlax-put-property (vlax-get-property xs 'Range (strcat (EX_GEX tipo_col) (itoa r))) 'Value2 assigned_tipo))
                        )
                        (if (not dent_code)
                          (setq dent_code (EX_BuscarDentCode (EX_DiametroDecimal dia_val) *forma_sel* *mat_sel* "IN" assigned_tipo))
                        )
                        (if dent_code
                          (progn
                            (vlax-put-property (vlax-get-property xs 'Range (strcat (EX_GEX spm_col) (itoa r))) 'Value2 dent_code)
                          )
                        )
                      )
                    )
                    (setq r (1+ r))
                  )
                )
                (setq i (1+ i))
              )
              (vl-catch-all-apply 'vlax-invoke (list (vlax-get-property (vlax-get-property xs 'Range "A1") 'CurrentRegion) 'AutoFilter))
              (vl-catch-all-apply 'vlax-invoke (list (vlax-get-property xs 'UsedRange) 'Sort (vlax-get-property xs 'Range "A2") 1))
              (setq cr (+ r 3) start_cr cr)
              (if (> ft 0.0) (setq cr (EX_AnexoTEE xs cr (strcat (EX_GEX 54) "2:" (EX_GEX 54) (itoa (1- r))))))
              (if (> fc 0.0) (setq cr (EX_AnexoCond xs cr (strcat (EX_GEX 55) "2:" (EX_GEX 55) (itoa (1- r))))))
              (if hm 
                (progn 
                  (setq range_str (strcat (EX_GEX mi) "2:" (EX_GEX mi) (itoa (1- r)))) 
                  (setq cr (EX_AnexoPipe xs cr range_str mi))
                )
              )
              
              (setq cr_side start_cr)
              (if cond_counts (setq cr_side (EX_AnexoTipos xs cr_side cond_counts *forma_sel* *mat_sel*)))
              (if reductor_counts (setq cr_side (EX_AnexoReductores xs cr_side reductor_counts)))
              (if tee_detailed_counts (setq cr_side (EX_AnexoTEEDetalle xs cr_side tee_detailed_counts *forma_sel* *mat_sel*)))

              (if pipe_sums 
                (progn 
                  (setq cr_side (EX_AnexoTuberiaRigida xs cr_side pipe_sums *mat_sel*)) 
                  (setq cr_side (EX_AnexoCondC xs cr_side pipe_sums *forma_sel* *mat_sel*)) 
                  (setq cr_side (EX_AnexoExpansion xs cr_side pipe_sums *forma_sel* *mat_sel*)) 
                )
              )

              (setq total_tapas '())
              (if cond_counts
                (foreach item cond_counts
                  (setq it (assoc (car item) total_tapas))
                  (if it
                    (setq total_tapas (subst (cons (car item) (+ (cdr it) (cdr item))) it total_tapas))
                    (setq total_tapas (cons item total_tapas))
                  )
                )
              )
              (if tee_detailed_counts
                (foreach item tee_detailed_counts
                  (setq it (assoc (car item) total_tapas))
                  (if it
                    (setq total_tapas (subst (cons (car item) (+ (cdr it) (cdr item))) it total_tapas))
                    (setq total_tapas (cons item total_tapas))
                  )
                )
              )
              (if pipe_sums
                (foreach item pipe_sums
                  (setq pz_c (fix (+ (/ (/ (cdr item) 1000.0) 9.0) 0.999999)))
                  (setq it (assoc (car item) total_tapas))
                  (if it
                    (setq total_tapas (subst (cons (car item) (+ (cdr it) pz_c)) it total_tapas))
                    (setq total_tapas (cons (cons (car item) pz_c) total_tapas))
                  )
                )
              )
              (if total_tapas (setq cr_side (EX_AnexoTapasEmpacaduras xs cr_side total_tapas *forma_sel* *mat_sel*)))
              (setq cr (max cr cr_side))

              (vlax-invoke-method (vlax-get-property (vlax-get-property xs 'Cells) 'Columns) 'AutoFit)
              (vl-catch-all-apply 'vlax-put-property (list (vlax-get-property xs 'Range (strcat (EX_GEX mi) ":" (EX_GEX 55))) 'Hidden :vlax-true))
              (princ (strcat "\n>>> REPORTE MM GENERADO OK (LB=40%) <<<"))
            )
            (alert "No se seleccionaron bloques.")
          )
        )
      )
    )
  )
  (if (and df (vl-file-size df)) (vl-file-delete df)) (princ)
)

(princ "\n--- EXCEL PRO v9.8.2 [METRICO] CARGADO ---") (princ)
